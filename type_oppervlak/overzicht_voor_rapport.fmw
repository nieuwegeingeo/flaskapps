FME workspace overzicht_voor_rapport.fmw

Parameters:
- DestDataset_JPEG = $(FME_MF_DIR_USERTYPED)producten   # Destination JPEG Folder
- SourceDataset_WMS = http://gng-ap713.nieuwegein.nl/mapproxy/service?REQUEST=GetCapabilities   # Source WMS (Web Map Service) URL
- WMS_IN_SEARCH_ENVELOPE_MINX_WMS = 133008.47500000001   # Minimum X
- WMS_IN_SEARCH_ENVELOPE_MINY_WMS = 450164.74900000001   # Minimum Y
- WMS_IN_SEARCH_ENVELOPE_MAXX_WMS = 134120.748931751   # Maximum X
- WMS_IN_SEARCH_ENVELOPE_MAXY_WMS = 451365.96299999999   # Maximum Y
- SourceDataset_GEOPACKAGE = $(FME_MF_DIR)producten\opp_type_polygon.gpkg   # Source GeoPackage File(s)
- DestDataset_PNGRASTER = $(FME_MF_DIR)producten   # Destination PNG (Portable Network Graphics) Folder

Readers:
- WMS_1: WMS from $(SourceDataset_WMS) in EPSG:28992
- GEOPACKAGE_1: GEOPACKAGE from $(SourceDataset_GEOPACKAGE) in EPSG:28992

Writers:
- JPEG_1: JPEG to $(DestDataset_JPEG) in EPSG:28992
- PNGRASTER_1: PNGRASTER to $(DestDataset_PNGRASTER) in EPSG:28992

basistopo (reader WMS_1)
    attributes: wms_service_name memo, wms_service_title memo, wms_service_abstract memo, wms_layer_name memo, wms_layer_title memo, wms_layer_abstract memo, wms_selected_layers set(basistopo)
    -> RasterExtractor
RasterExtractor
    RASTER_FORMAT = PNG (Portable Network Graphics)
    RASTER_FORMAT_ATTR = _rasterFormatName
    RASTER_BLOB_ATTR = _rasterBlob
    -> RasterBandAdder
RasterBandAdder
    CELL_VALUE = 255
    INTERPRETATION = Alpha8
    -> RasterMosaicker
opp_type_polygon (reader GEOPACKAGE_1)
    attributes: Type text(200), Wijk text(200), Oppervlak text(200)
    -> TestFilter
TestFilter
    TEST_LIST = BOOL_OP,OR,COMPOSITE_TEST,<Unused>,TEST_CLAUSE,"TEST @Value(Type) = Bebouwd",@Value(Type) = Bebouwd,BOOL_OP,OR,COMPOSITE_TEST,<Unused>,TEST_CLAUSE,"TEST @Value(Type) = Groen",@Value(Type) = Groen,BOOL_OP,OR,COMPOSITE_TEST,<Unused>,TEST_CLAUSE,"TEST @Value(Type) = Onverhard",@Value(Type) = Onverhard,BOOL_OP,OR,COMPOSITE_TEST,<Unused>,TEST_CLAUSE,"TEST @Value(Type) = Verhard",@Value(Type) = Verhard,BOOL_OP,OR,COMPOSITE_TEST,<Unused>,TEST_CLAUSE,"TEST @Value(Type) = Erf",@Value(Type) = Erf,BOOL_OP,OR,COMPOSITE_TEST,<Unused>,TEST_CLAUSE,"TEST @Value(Type) = Water",@Value(Type) = Water,BOOL_OP,OR,COMPOSITE_TEST,<Unused>,TEST_CLAUSE,"TEST @Value(Type) = Onbekend",@Value(Type) = Onbekend
    DEFAULT_VALUE = <UNFILTERED>
    @Value(Type) = Bebouwd -> FeatureColorSetter
    @Value(Type) = Groen -> FeatureColorSetter_2
    @Value(Type) = Onverhard -> FeatureColorSetter_3
    @Value(Type) = Verhard -> FeatureColorSetter_4
    @Value(Type) = Erf -> FeatureColorSetter_5
    @Value(Type) = Water -> FeatureColorSetter_6
    @Value(Type) = Onbekend -> FeatureColorSetter_7
FeatureColorSetter
    FILL_COLOR = 1,0,0
    MODE = Fixed
    COLOR = 1,0,0
    COLORED -> ImageRasterizer
FeatureColorSetter_2
    FILL_COLOR = 0.666667,1,0.498039
    MODE = Fixed
    COLOR = 0.666667,1,0.498039
    COLORED -> ImageRasterizer
FeatureColorSetter_3
    FILL_COLOR = 0.811765,0.811765,0.811765
    MODE = Fixed
    COLOR = 0.811765,0.811765,0.811765
    COLORED -> ImageRasterizer
FeatureColorSetter_4
    FILL_COLOR = 0.603922,0.603922,0.603922
    MODE = Fixed
    COLOR = 0.603922,0.603922,0.603922
    COLORED -> ImageRasterizer
FeatureColorSetter_5
    FILL_COLOR = 0.666667,0.333333,0
    MODE = Fixed
    COLOR = 0.666667,0.333333,0
    COLORED -> ImageRasterizer
FeatureColorSetter_6
    FILL_COLOR = 0,0.854902,0.854902
    MODE = Fixed
    COLOR = 0,0.854902,0.854902
    COLORED -> ImageRasterizer
FeatureColorSetter_7
    FILL_COLOR = 1,1,1
    MODE = Fixed
    COLOR = 1,1,1
    COLORED -> ImageRasterizer
ImageRasterizer
    ANTI_ALIASING = Yes
    X_CELL_SIZE = 0.5
    BACKGROUND_ALPHA = 0
    INTERPRETATION_TYPE = RGBA32
    BACKGROUND_COLOR = 0,0,0
    FILL_WITH_NODATA = No
    ROWCOL_OR_CELLSIZE = CellSize
    Y_CELL_SIZE = 0.5
    ALPHA = 1
    SPECIFY_GROUND_EXTENTS = Use input data ground extents
    RASTER -> RasterMosaicker
RasterMosaicker
    COMPOSITE_USING_ALPHA_BAND_NAME = Yes
    NODATA_OVERWRITE = No
    INTERPOLATION_TYPE_NAME = Bicubic
    MERGE_PALETTES_NAME = No
    SNAPPING_TYPE_NAME = Resample
    ACCUM_ATTRS_NAME = Get Attributes From One Representative Feature
    -> RasterSelector
    -> rapport_foto (writer PNGRASTER_1)
rapport_foto (writer PNGRASTER_1)
    attributes: wms_service_name char(254), wms_service_title char(254), wms_service_abstract char(254), wms_layer_name char(254), wms_layer_title char(254), wms_layer_abstract char(254), wms_selected_layers char(10), _rasterBlob char(200), _rasterFormatName char(200)
RasterSelector [off]
    BAND_LIST = 3
    SELECTION_MODE = Band and Palette List
    -> RasterBandRemover
RasterBandRemover [off]
    -> rapport_foto (writer JPEG_1)
rapport_foto (writer JPEG_1) [off]
    attributes: wms_service_name char(254), wms_service_title char(254), wms_service_abstract char(254), wms_layer_name char(254), wms_layer_title char(254), wms_layer_abstract char(254), wms_selected_layers char(15)
Sorter
    SORT_PARM = fme_basename ALPHA DESCENDING
