FME workspace type_oppervlak.fmw

Parameters:
- EMAIL = m.kselik@nieuwegein.nl   # Email
- WIJKEN_SELECT = Stadscentrum   # Selecteer wijken
- OUTPUT_TYPE = beide   # PDF of Excel

Creator_3
    GEOMTYPE = Geometry Object
    NUM = 1
    CREATED -> SystemCaller_2
SystemCaller_2
    CMD = del /q c:\programs\flask\type_oppervlak\producten\*
    -> Tester_3
    -> FeatureReader [INITIATOR]
FeatureReader
    ATTR_ACCUM_MODE = Only Use Result
    ORACLE_SPATIAL_USE_SEARCH_ENVELOPE = NO
    ORACLE_SPATIAL_USE_UNIFIED_DATE_ATTRS = YES
    ORACLE_SPATIAL_READ_3D_POLYGON_AS_FACE = NO
    INTERACT = <No Spatial Filter>
    ORACLE_SPATIAL_PARSE_MAPINFO_SYMBOLOGY = NO
    ORACLE_SPATIAL_CLIP_TO_ENVELOPE = NO
    ORACLE_SPATIAL_CHUNK_SIZE = 200
    FEATURETYPES = NIEUWEGEIN.GM_SP_WIJKEN
    COMBINE_GEOM = Use Result
    ORACLE_SPATIAL_PASSWORD =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
    ORACLE_SPATIAL_QUERY_FEATURE_TYPES_FOR_MERGE_FILTERS = Yes
    OUTPUT_FEATURES_DISPLAY = Schema and Data Features
    ORACLE_SPATIAL_USER_NAME = NIEUWEGEIN
    ORACLE_SPATIAL_REMOVE_SCHEMA_QUALIFIER = NO
    ORACLE_SPATIAL_SERVER_TYPE = ORACLE8i
    ORACLE_SPATIAL_PERSISTENT_CONNECTION = YES
    ORACLE_SPATIAL_INTERRESULT = = 'TRUE'
    DATASET = vngp
    ORACLE_SPATIAL_HANDLE_MULTIPLE_SPATIAL_COLUMNS = NO
    ORACLE_SPATIAL_INTERACTION = ANYINTERACT
    FORMAT = ORACLE_SPATIAL
    ATTRIBUTES = NIEUWEGEIN.GM_SP_WIJKEN,"WIJKKODE,WIJKNAAM,ADRESSEN,ID"
    ORACLE_SPATIAL_SHOW_SYSTEM_TABLES = NO
    NIEUWEGEIN.GM_SP_WIJKEN -> Tester
Note: Selecteer wijk
Tester
    TEST_DESCRIPTION = ""
    TEST_CLAUSE = TEST @Value(WIJKNAAM) IN $(WIJKEN_SELECT)
    BOOL_OP = AND
    TEST_MODE = Automatic
    PASSED -> BGT_Object_selector [Wijken]
Note: Selecteert de BGT objecten en clipt ze naar wijk
BGT_Object_selector: BGT Object selector
    Begroeidterreindeel -> Aggregator_2
    Bebouwd -> Aggregator_3
    Onbegroeidterreindeel -> Aggregator_4
    Waterdeel -> Aggregator_5
    Ondersteunend_Waterdeel -> Aggregator_6
    Ondersteunend_wegdeel -> Aggregator_7
    Overbruggingsdeel -> Aggregator_8
    Wegdeel -> Aggregator_9
Aggregator_2
    AGGREGATE_TYPE = Homogeneous Collection (If Possible)
    ORDERED = No
    ACCUM_ATTRS_NAME = Get Attributes From One Representative Feature
    SEP = ,
    MODE = Geometry - Assemble One Level
    GROUP_BY = wijken_WIJKNAAM BGTFYSIEKVOORKOMEN
    AGGREGATE -> AttributeManager_3
AttributeManager_3
    ATTR_TABLE:
      REMOVE wijken_WIJKKODE
      REMOVE wijken_ADRESSEN
      REMOVE wijken_ID
      REMOVE IDENTIFICATIE
      REMOVE OBJECTBEGINTIJD
      REMOVE OBJECTEINDTIJD
      REMOVE TIJDSTIPREGISTRATIE
      REMOVE EINDREGISTRATIE
      REMOVE LV_PUBLICATIEDATUM
      REMOVE BRONHOUDER
      REMOVE BGTSTATUS
      REMOVE PLUSSTATUS
      REMOVE INONDERZOEK
      REMOVE BEGROEIDTERREINDEELOPTALUD
      REMOVE RELATIEVEHOOGTELIGGING
      REMOVE PLUSFYSIEKVOORKOMEN
      REMOVE SYS_FILTEREN
      REMOVE BOR_ID
      REMOVE XFM_ID
      REMOVE BORBEHEERDER
      REMOVE CUSTOMFYSIEKVOORKOMEN
      REMOVE _clipped
    -> Junction
Aggregator_3
    AGGREGATE_TYPE = Homogeneous Collection (If Possible)
    ORDERED = No
    ACCUM_ATTRS_NAME = Get Attributes From One Representative Feature
    SEP = ,
    MODE = Geometry - Assemble One Level
    GROUP_BY = wijken_WIJKNAAM
    AGGREGATE -> AttributeManager_4
AttributeManager_4
    ATTR_TABLE:
      REMOVE BGTSTATUS
      REMOVE wijken_WIJKKODE
      REMOVE wijken_ADRESSEN
      REMOVE wijken_ID
      REMOVE IDENTIFICATIE
      REMOVE OBJECTBEGINTIJD
      REMOVE OBJECTEINDTIJD
      REMOVE TIJDSTIPREGISTRATIE
      REMOVE EINDREGISTRATIE
      REMOVE LV_PUBLICATIEDATUM
      REMOVE BRONHOUDER
      REMOVE PLUSSTATUS
      REMOVE INONDERZOEK
      REMOVE RELATIEVEHOOGTELIGGING
      REMOVE PLUSTYPE
      REMOVE SYS_FILTEREN
      REMOVE BOR_ID
      REMOVE XFM_ID
      REMOVE BORBEHEERDER
      REMOVE CUSTOMTYPE
      REMOVE IDENTIFICATIEBAGPND
      REMOVE NUMAANDUIDINGVISUALISATIE
      REMOVE _clipped
    -> Junction_2
Note: bebouwd
Junction_2
    -> AttributeManager_11
AttributeManager_11
    ATTR_TABLE:
      RENAME_SET_VALUE wijken_WIJKNAAM > Wijk
      REMOVE BGTTYPE
      SET_TO Type = Bebouwd
    -> AttributeManager_17_OUTPUT_-__Aggregator_16
Aggregator_4
    AGGREGATE_TYPE = Homogeneous Collection (If Possible)
    ORDERED = No
    ACCUM_ATTRS_NAME = Get Attributes From One Representative Feature
    SEP = ,
    MODE = Geometry - Assemble One Level
    GROUP_BY = wijken_WIJKNAAM BGTFYSIEKVOORKOMEN
    AGGREGATE -> AttributeManager_5
AttributeManager_5
    ATTR_TABLE:
      REMOVE BGTSTATUS
      REMOVE wijken_WIJKKODE
      REMOVE wijken_ADRESSEN
      REMOVE wijken_ID
      REMOVE IDENTIFICATIE
      REMOVE OBJECTBEGINTIJD
      REMOVE OBJECTEINDTIJD
      REMOVE TIJDSTIPREGISTRATIE
      REMOVE EINDREGISTRATIE
      REMOVE LV_PUBLICATIEDATUM
      REMOVE BRONHOUDER
      REMOVE PLUSSTATUS
      REMOVE INONDERZOEK
      REMOVE RELATIEVEHOOGTELIGGING
      REMOVE SYS_FILTEREN
      REMOVE BOR_ID
      REMOVE XFM_ID
      REMOVE BORBEHEERDER
      REMOVE _clipped
      SET_TO
      REMOVE ONBEGROEIDTERREINDEELOPTALUD
      REMOVE PLUSFYSIEKVOORKOMEN
      REMOVE CUSTOMFYSIEKVOORKOMEN
    -> TestFilter_3
TestFilter_3
    TEST_LIST = BOOL_OP,OR,COMPOSITE_TEST,<Unused>,TEST_CLAUSE,"TEST @Value(BGTFYSIEKVOORKOMEN) = zand",Zand,BOOL_OP,OR,COMPOSITE_TEST,<Unused>,TEST_CLAUSE,"TEST @Value(BGTFYSIEKVOORKOMEN) = erf",Erf,BOOL_OP,OR,COMPOSITE_TEST,<Unused>,TEST_CLAUSE,"TEST @Value(BGTFYSIEKVOORKOMEN) IN open verharding,half verhard,gesloten verharding",Verhard,BOOL_OP,OR,COMPOSITE_TEST,<Unused>,TEST_CLAUSE,"TEST @Value(BGTFYSIEKVOORKOMEN) = onverhard",Onverhard,BOOL_OP,OR,COMPOSITE_TEST,<Unused>,TEST_CLAUSE,"TEST @Value(BGTFYSIEKVOORKOMEN) = transitie",Transitie
    DEFAULT_VALUE = <UNFILTERED>
    Zand -> Junction_5
    Erf -> Junction_6
    Verhard -> Junction_3
    Onverhard -> Junction_5
    Transitie -> Junction_4
    <UNFILTERED> -> TestFilter_3__Unfiltered_
TestFilter_3__Unfiltered_: Inspector
Note: erf
Junction_6
    -> AttributeManager_13
AttributeManager_13
    ATTR_TABLE:
      RENAME_SET_VALUE wijken_WIJKNAAM > Wijk
      REMOVE BGTFYSIEKVOORKOMEN
      SET_TO Type = Erf
    -> AttributeManager_17_OUTPUT_-__Aggregator_16
Aggregator_5
    AGGREGATE_TYPE = Homogeneous Collection (If Possible)
    ORDERED = No
    ACCUM_ATTRS_NAME = Get Attributes From One Representative Feature
    SEP = ,
    MODE = Geometry - Assemble One Level
    GROUP_BY = BGTTYPE wijken_WIJKNAAM
    AGGREGATE -> AttributeManager_6
AttributeManager_6
    ATTR_TABLE:
      REMOVE wijken_WIJKKODE
      REMOVE wijken_ADRESSEN
      REMOVE wijken_ID
      REMOVE IDENTIFICATIE
      REMOVE OBJECTBEGINTIJD
      REMOVE OBJECTEINDTIJD
      REMOVE TIJDSTIPREGISTRATIE
      REMOVE EINDREGISTRATIE
      REMOVE LV_PUBLICATIEDATUM
      REMOVE BRONHOUDER
      REMOVE BGTSTATUS
      REMOVE PLUSSTATUS
      REMOVE INONDERZOEK
      REMOVE DROOGVALLEND
      REMOVE RELATIEVEHOOGTELIGGING
      REMOVE PLUSTYPE
      REMOVE SYS_FILTEREN
      REMOVE BOR_ID
      REMOVE XFM_ID
      REMOVE BORBEHEERDER
      REMOVE CUSTOMTYPE
      REMOVE _clipped
    -> TestFilter_6
TestFilter_6
    TEST_LIST = BOOL_OP,OR,COMPOSITE_TEST,<Unused>,TEST_CLAUSE,"TEST @Value(BGTTYPE) IN watervlakte,waterloop",Watervlakte,waterloop,BOOL_OP,OR,COMPOSITE_TEST,<Unused>,TEST_CLAUSE,"TEST @Value(BGTTYPE) = greppel, droge sloot",Greppel, droge sloot,BOOL_OP,OR,COMPOSITE_TEST,<Unused>,TEST_CLAUSE,"TEST @Value(BGTTYPE) = transitie",Transitie
    DEFAULT_VALUE = <UNFILTERED>
    Watervlakte,waterloop -> Junction_7
    Greppel, droge sloot -> Junction_5
    Transitie -> Junction_4
    <UNFILTERED> -> TestFilter_6__Unfiltered_
TestFilter_6__Unfiltered_: Inspector
Note: water
Junction_7
    -> AttributeManager_16
AttributeManager_16
    ATTR_TABLE:
      RENAME_SET_VALUE wijken_WIJKNAAM > Wijk
      SET_TO Type = Water
      REMOVE BGTTYPE
    -> AttributeManager_17_OUTPUT_-__Aggregator_16
Aggregator_6
    AGGREGATE_TYPE = Homogeneous Collection (If Possible)
    ORDERED = No
    ACCUM_ATTRS_NAME = Get Attributes From One Representative Feature
    SEP = ,
    MODE = Geometry - Assemble One Level
    GROUP_BY = BGTTYPE wijken_WIJKNAAM
    AGGREGATE -> AttributeManager_7
AttributeManager_7
    ATTR_TABLE:
      REMOVE wijken_WIJKKODE
      REMOVE wijken_ADRESSEN
      REMOVE wijken_ID
      REMOVE IDENTIFICATIE
      REMOVE OBJECTBEGINTIJD
      REMOVE OBJECTEINDTIJD
      REMOVE TIJDSTIPREGISTRATIE
      REMOVE EINDREGISTRATIE
      REMOVE LV_PUBLICATIEDATUM
      REMOVE BRONHOUDER
      REMOVE BGTSTATUS
      REMOVE PLUSSTATUS
      REMOVE INONDERZOEK
      REMOVE DROOGVALLEND
      REMOVE RELATIEVEHOOGTELIGGING
      REMOVE PLUSTYPE
      REMOVE SYS_FILTEREN
      REMOVE BOR_ID
      REMOVE XFM_ID
      REMOVE BORBEHEERDER
      REMOVE CUSTOMTYPE
      REMOVE _clipped
    -> Junction
Aggregator_7
    AGGREGATE_TYPE = Homogeneous Collection (If Possible)
    ORDERED = No
    ACCUM_ATTRS_NAME = Get Attributes From One Representative Feature
    SEP = ,
    MODE = Geometry - Assemble One Level
    GROUP_BY = wijken_WIJKNAAM BGTFYSIEKVOORKOMEN
    AGGREGATE -> AttributeManager_8
AttributeManager_8
    ATTR_TABLE:
      REMOVE wijken_WIJKKODE
      REMOVE wijken_ADRESSEN
      REMOVE wijken_ID
      REMOVE IDENTIFICATIE
      REMOVE OBJECTBEGINTIJD
      REMOVE OBJECTEINDTIJD
      REMOVE TIJDSTIPREGISTRATIE
      REMOVE EINDREGISTRATIE
      REMOVE LV_PUBLICATIEDATUM
      REMOVE BRONHOUDER
      REMOVE BGTSTATUS
      REMOVE PLUSSTATUS
      REMOVE INONDERZOEK
      REMOVE ONDERSTEUNENDWEGDEELOPTALUD
      REMOVE RELATIEVEHOOGTELIGGING
      REMOVE BGTFUNCTIE
      REMOVE PLUSFUNCTIE
      REMOVE PLUSFYSIEKVOORKOMEN
      REMOVE SYS_FILTEREN
      REMOVE BOR_ID
      REMOVE XFM_ID
      REMOVE BORBEHEERDER
      REMOVE CUSTOMFUNCTIE
      REMOVE CUSTOMFYSIEKVOORKOMEN
      REMOVE _clipped
    -> TestFilter_4
TestFilter_4
    TEST_LIST = BOOL_OP,OR,COMPOSITE_TEST,<Unused>,TEST_CLAUSE,"TEST @Value(BGTFYSIEKVOORKOMEN) = zand",Zand,BOOL_OP,OR,COMPOSITE_TEST,<Unused>,TEST_CLAUSE,"TEST @Value(BGTFYSIEKVOORKOMEN) = groenvoorziening",Groenvoorziening,BOOL_OP,OR,COMPOSITE_TEST,<Unused>,TEST_CLAUSE,"TEST @Value(BGTFYSIEKVOORKOMEN) IN open verharding,half verhard,gesloten verharding",verharding,BOOL_OP,OR,COMPOSITE_TEST,<Unused>,TEST_CLAUSE,"TEST @Value(BGTFYSIEKVOORKOMEN) = transitie",Transitie,BOOL_OP,OR,COMPOSITE_TEST,<Unused>,TEST_CLAUSE,"TEST @Value(BGTFYSIEKVOORKOMEN) = onverhard",Onverhard
    DEFAULT_VALUE = <UNFILTERED>
    Zand -> Junction_5
    Groenvoorziening -> Junction
    verharding -> Junction_3
    Transitie -> Junction_4
    Onverhard -> Junction_5
    <UNFILTERED> -> TestFilter_4__Unfiltered_
Note: groen
Junction
    -> AttributeManager_12
AttributeManager_12
    ATTR_TABLE:
      RENAME_SET_VALUE wijken_WIJKNAAM > Wijk
      REMOVE BGTTYPE
      REMOVE BGTFYSIEKVOORKOMEN
      SET_TO Type = Groen
    -> AttributeManager_17_OUTPUT_-__Aggregator_16
TestFilter_4__Unfiltered_: Inspector
Aggregator_8
    AGGREGATE_TYPE = Homogeneous Collection (If Possible)
    ORDERED = No
    ACCUM_ATTRS_NAME = Get Attributes From One Representative Feature
    SEP = ,
    MODE = Geometry - Assemble One Level
    GROUP_BY = wijken_WIJKNAAM
    AGGREGATE -> AttributeManager_9
AttributeManager_9
    ATTR_TABLE:
      REMOVE wijken_WIJKKODE
      REMOVE wijken_ADRESSEN
      REMOVE wijken_ID
      REMOVE IDENTIFICATIE
      REMOVE OBJECTBEGINTIJD
      REMOVE OBJECTEINDTIJD
      REMOVE TIJDSTIPREGISTRATIE
      REMOVE EINDREGISTRATIE
      REMOVE LV_PUBLICATIEDATUM
      REMOVE BRONHOUDER
      REMOVE BGTSTATUS
      REMOVE PLUSSTATUS
      REMOVE INONDERZOEK
      REMOVE OVERBRUGGINGISBEWEEGBAAR
      REMOVE RELATIEVEHOOGTELIGGING
      REMOVE TYPEOVERBRUGGINGSDEEL
      REMOVE HOORTBIJTYPEOVERBRUGGING
      REMOVE SYS_FILTEREN
      REMOVE BOR_ID
      REMOVE XFM_ID
      REMOVE BORBEHEERDER
      REMOVE CUSTOMTYPEOVERBRUGGINGSDEEL
      REMOVE CUSTOMHOORTBIJTYPEOVERBRUGGING
      REMOVE _clipped
    -> Junction_3
Aggregator_9
    AGGREGATE_TYPE = Homogeneous Collection (If Possible)
    ORDERED = No
    ACCUM_ATTRS_NAME = Get Attributes From One Representative Feature
    SEP = ,
    MODE = Geometry - Assemble One Level
    GROUP_BY = BGTFYSIEKVOORKOMEN wijken_WIJKNAAM
    AGGREGATE -> AttributeManager_10
AttributeManager_10
    ATTR_TABLE:
      REMOVE wijken_WIJKKODE
      REMOVE wijken_ADRESSEN
      REMOVE wijken_ID
      REMOVE IDENTIFICATIE
      REMOVE OBJECTBEGINTIJD
      REMOVE OBJECTEINDTIJD
      REMOVE TIJDSTIPREGISTRATIE
      REMOVE EINDREGISTRATIE
      REMOVE LV_PUBLICATIEDATUM
      REMOVE BRONHOUDER
      REMOVE BGTSTATUS
      REMOVE PLUSSTATUS
      REMOVE INONDERZOEK
      REMOVE RELATIEVEHOOGTELIGGING
      REMOVE SYS_FILTEREN
      REMOVE BOR_ID
      REMOVE XFM_ID
      REMOVE BORBEHEERDER
      REMOVE _clipped
      REMOVE WEGDEELOPTALUD
      REMOVE BGTFUNCTIE
      REMOVE PLUSFUNCTIE
      REMOVE PLUSFYSIEKVOORKOMEN
      REMOVE CUSTOMFUNCTIE
      REMOVE CUSTOMFYSIEKVOORKOMEN
    -> TestFilter_5
TestFilter_5
    TEST_LIST = BOOL_OP,OR,COMPOSITE_TEST,<Unused>,TEST_CLAUSE,"TEST @Value(BGTFYSIEKVOORKOMEN) IN open verharding,half verhard,gesloten verharding",Verhard,BOOL_OP,OR,COMPOSITE_TEST,<Unused>,TEST_CLAUSE,"TEST @Value(BGTFYSIEKVOORKOMEN) = onverhard",Onverhard,BOOL_OP,OR,COMPOSITE_TEST,<Unused>,TEST_CLAUSE,"TEST @Value(BGTFYSIEKVOORKOMEN) = transitie",Transitie
    DEFAULT_VALUE = <UNFILTERED>
    Verhard -> Junction_3
    Onverhard -> Junction_5
    Transitie -> Junction_4
    <UNFILTERED> -> TestFilter_5__Unfiltered_
Note: onverhard
Junction_5
    -> AttributeManager_14
AttributeManager_14
    ATTR_TABLE:
      RENAME_SET_VALUE wijken_WIJKNAAM > Wijk
      REMOVE BGTFYSIEKVOORKOMEN
      SET_TO Type = Onverhard
      REMOVE BGTTYPE
    -> AttributeManager_17_OUTPUT_-__Aggregator_16
Note: verhard
Junction_3
    -> AttributeManager_15
AttributeManager_15
    ATTR_TABLE:
      RENAME_SET_VALUE wijken_WIJKNAAM > Wijk
      REMOVE BGTFYSIEKVOORKOMEN
      SET_TO Type = Verhard
    -> AttributeManager_17_OUTPUT_-__Aggregator_16
Note: onbekend
Junction_4
    -> AttributeManager_17
AttributeManager_17
    ATTR_TABLE:
      RENAME_SET_VALUE wijken_WIJKNAAM > Wijk
      SET_TO Type = Onbekend
      REMOVE BGTTYPE
      REMOVE BGTFYSIEKVOORKOMEN
    -> AttributeManager_17_OUTPUT_-__Aggregator_16
AttributeManager_17_OUTPUT_-__Aggregator_16: Junction
    -> Aggregator_16
    -> Aggregator_10
TestFilter
    TEST_LIST = BOOL_OP,OR,COMPOSITE_TEST,<Unused>,TEST_CLAUSE,"TEST $(OUTPUT_TYPE) = pdf",PDF,BOOL_OP,OR,COMPOSITE_TEST,<Unused>,TEST_CLAUSE,"TEST $(OUTPUT_TYPE) = excel",Excel,BOOL_OP,OR,COMPOSITE_TEST,<Unused>,TEST_CLAUSE,"TEST $(OUTPUT_TYPE) = beide",Beide
    DEFAULT_VALUE = <UNFILTERED>
    PDF -> Tester_7_PASSED_-__AttributeCreator
    Excel -> FeatureWriter [Elements]
    Beide -> FeatureWriter [Elements]
    Beide -> Tester_7_PASSED_-__AttributeCreator
Tester_7_PASSED_-__AttributeCreator: Junction
    -> Aggregator
    -> FeatureWriter_3 [Aggregate]
    -> AttributeManager_2
AttributeCreator_4
    ATTR_TABLE = SET_TO mail_pass = 1
    -> FeatureHolder_2
Note: Per wijk alleen bij Excel of Beide
Tester_2
    TEST_DESCRIPTION = ""
    TEST_CLAUSE:
      TEST $(OUTPUT_TYPE) = excel
      TEST $(OUTPUT_TYPE) = beide
    BOOL_OP = OR
    TEST_MODE = Automatic
    PASSED -> FeatureWriter [Sorted]
FeatureHolder_2
    -> Tester_4
ZipArchiver_2
    MODE = REMOVE
    FILE_PATH = @Value(_dataset)
    ZIP_PATH = $(FME_MF_DIR_ENCODED)producten\oppervlak_download.zip
    -> FeatureHolder_3
FeatureHolder_3
    -> ZipArchiver
ZipArchiver
    MODE = APPEND
    FILE_PATH = @Value(_dataset)
    ZIP_PATH = $(FME_MF_DIR_ENCODED)producten\oppervlak_download.zip
    LogSuccess -> Tester_5
TestFilter_5__Unfiltered_: Inspector

Bookmark: Totaal opp berekenen
Aggregator_10
    AGGREGATE_TYPE = Homogeneous Collection (If Possible)
    ORDERED = No
    ACCUM_ATTRS_NAME = Get Attributes From One Representative Feature
    SEP = ,
    MODE = Geometry - Assemble One Level
    GROUP_BY = Type
    AGGREGATE -> AreaCalculator_2
AreaCalculator_2
    AREA_TYPE = Plane Area
    AREA_ATTR = Oppervlak
    MULT = 1
    -> AttributeRounder_2
AttributeRounder_2
    PLACES = 2
    ROUND_TYPE = Nearest
    SRC_ATTRS = Oppervlak
    -> SpatialFilter [Candidate]
    -> Aggregator_11
Aggregator_11
    AGGREGATE_TYPE = Homogeneous Collection (If Possible)
    ORDERED = No
    ACCUM_ATTRS_NAME = Get Attributes From One Representative Feature
    SUM = Oppervlak
    SEP = ,
    MODE = Geometry - Assemble One Level
    AGGREGATE -> AttributeManager_18
AttributeManager_18
    ATTR_TABLE:
      RENAME_SET_VALUE Oppervlak > Opp_TOTAAL
      REMOVE Type
      REMOVE Wijk
    -> SpatialFilter [Filter]
SpatialFilter
    AGGREGATE_HANDLING = Yes
    ATTR_ACCUM_MODE = Merge Filter
    PASS_CRITERIA = Pass Against One Filter
    USE_BOUNDING_BOX = No
    CURVE_BOUNDARY_RULE_PARAM = Default Rule
    PREDICATES = INTERSECTS
    PREDATTR = _predicate
    ATTR_CONFLICT_RES = Use Candidate
    BASE_TYPE = Multiple Filters
    PASSED -> Sorter_3
Sorter_3
    SORT_PARM = Wijk ALPHA ASCENDING Type ALPHA ASCENDING
    SORTED -> AttributeCreator_3
AttributeCreator_3
    ATTR_TABLE = SET_TO Percentage = @round(@mult(@div(@Value(Oppervlak),@Value(Opp_TOTAAL)),100))
    -> AttributeManager
AttributeManager
    ATTR_TABLE:
      SET_TO Wijk = Totaal
      REMOVE Opp_TOTAAL
      REMOVE _predicate
    -> AttributeRounder
AttributeRounder
    PLACES = 0
    ROUND_TYPE = Nearest
    SRC_ATTRS = Percentage
    -> TestFilter

Bookmark: kaart extract
Aggregator
    AGGREGATE_TYPE = Homogeneous Collection (If Possible)
    ORDERED = No
    ACCUM_ATTRS_NAME = Get Attributes From One Representative Feature
    SEP = ,
    MODE = Geometry - Assemble One Level
    AGGREGATE -> BoundingBoxReplacer
BoundingBoxReplacer
    BOXTYPE = Bounding Box
    BOX -> Bufferer
Bufferer
    OFFSET = 100
    INTERP_SEGMENTS = 8
    CAP_STYLE = Round
    BUFFERED -> BoundsExtractor
BoundsExtractor
    XMIN = _xmin
    XMAX = _xmax
    ZMIN = _zmin
    ZMAX = _zmax
    YMAX = _ymax
    YMIN = _ymin
    -> FeatureHolder
FeatureWriter_3
    GEOPACKAGE_COORDINATE_SYSTEM_GRANULARITY = FEATURE_TYPE
    DATASET = $(FME_MF_DIR_ENCODED)producten\opp_type_polygon
    FORMAT = GEOPACKAGE
    WRITER_DIRECTIVES = OVERWRITE_DATASET,NO,TRANSACTION_SIZE,5000,DESTINATION_DATASETTYPE_VALIDATION,Yes,COORDINATE_SYSTEM_GRANULARITY,FEATURE_TYPE
    GEOPACKAGE_OVERWRITE_DATASET = NO
    GEOPACKAGE_TRANSACTION_SIZE = 5000
    FEATURE_TYPE_LIST_ATTR = _feature_type
    GEOPACKAGE_DESTINATION_DATASETTYPE_VALIDATION = Yes
    DATASET_ATTR = _dataset
    TOTAL_FEATURES_WRITTEN_ATTR = _total_features_written
    SUMMARY -> FeatureHolder
FeatureHolder
    -> GeometryFilter_3
GeometryFilter_3
    BREAK_AGG = No
    GEOM_PORT_NAMES = Area
    AREA -> WorkspaceRunner
WorkspaceRunner
    BLOCKING = Yes
    WORKSPACE_FILE = $(FME_MF_DIR)overzicht_voor_rapport.fmw
    WORKSPACE_PARAMETERS = DestDataset_JPEG,$(FME_MF_DIR_USERTYPED)producten,SourceDataset_WMS,http://gng-ap713.nieuwegein.nl/mapproxy/service?REQUEST=GetCapabilities,WMS_IN_SEARCH_ENVELOPE_MINX_WMS,@Value(_xmin),WMS_IN_SEARCH_ENVELOPE_MINY_WMS,@Value(_ymin),WMS_IN_SEARCH_ENVELOPE_MAXX_WMS,@Value(_xmax),WMS_IN_SEARCH_ENVELOPE_MAXY_WMS,@Value(_ymax),SourceDataset_GEOPACKAGE,$(FME_MF_DIR_USERTYPED)producten\opp_type_polygon.gpkg
    SUCCEEDED -> FeatureReader_2 [INITIATOR]

Bookmark: Rapport creator
FeatureReader_2
    ATTR_ACCUM_MODE = Only Use Result
    INTERACT = <No Spatial Filter>
    COORDSYS = EPSG:28992
    PNGRASTER_CLIP_TO_ENVELOPE = NO
    COMBINE_GEOM = Use Result
    PNGRASTER_USE_SEARCH_ENVELOPE = NO
    OUTPUT_FEATURES_DISPLAY = Schema and Data Features
    DATASET = $(FME_MF_DIR_ENCODED)producten\rapport_foto.png
    PNGRASTER_GROUP_BY_DATASET = Yes
    FORMAT = PNGRASTER
    ATTRIBUTES = rapport_foto,
    rapport_foto -> PDFPageFormatter [Rapport_foro]
PDFPageFormatter
    PAGE_UNITS = Inches
    PAGE_HEIGHT_USER = 11.69
    PAGE_WIDTH_PTS = 595
    PAGE_HEIGHT_PTS = 842
    PAGE_ORIENTATION = Portrait
    PAGE_NUMBER = 1
    PAGE_WIDTH_USER = 8.27
    PAGE_SIZE = A4
    PAGE_OBJECTS = "HTML TABLE SIZE_PARAMS;;WIDTH;581.04;HEIGHT;454.01;SCALING_PARAMS;;CLIPPING_ENABLED;No;MINX;7.2;MINY;12.9297;FIXED_ASPECT;Yes","Rapport_foro SIZE_PARAMS;;WIDTH;581.04;HEIGHT;360;SCALING_PARAMS;;CLIPPING_ENABLED;No;MINX;7.2;MINY;474.8;FIXED_ASPECT;Yes"
    -> FeatureWriter_2 [Output]
FeatureWriter_2
    DATASET = $(FME_MF_DIR_ENCODED)producten\Verblijfsobjecten_rapport.pdf
    PDF2D_DEFAULT_OPACITY = 0.4
    PDF2D_RICH_TEXT = No
    PDF2D_SCALE_TEXT_FONT = No
    FORMAT = PDF2D
    WRITER_DIRECTIVES = COMPRESS_STREAMS,Yes,PANEL_VISIBILITY,Layers,DEFAULT_OPACITY,0.4,DEFAULT_POINT_SIZE,1.0,RICH_TEXT,No,SCALE_TEXT_FONT,No,DESTINATION_DATASETTYPE_VALIDATION,Yes,PAGE_SIZE,Letter,DEFAULT_LINE_WIDTH,1.0,RANDOMIZE_FEATURE_TYPE_COLOR,Yes,WRITE_ATTRIBUTES,Yes,PDF14_COMPATIBLE,No
    PDF2D_COMPRESS_STREAMS = Yes
    PDF2D_WRITE_ATTRIBUTES = Yes
    PDF2D_PAGE_SIZE = Letter
    PDF2D_DEFAULT_POINT_SIZE = 1.0
    FEATURE_TYPE_LIST_ATTR = _feature_type
    PDF2D_PDF14_COMPATIBLE = No
    PDF2D_RANDOMIZE_FEATURE_TYPE_COLOR = Yes
    PDF2D_PANEL_VISIBILITY = Layers
    PDF2D_DESTINATION_DATASETTYPE_VALIDATION = Yes
    DATASET_ATTR = _dataset
    TOTAL_FEATURES_WRITTEN_ATTR = _total_features_written
    PDF2D_DEFAULT_LINE_WIDTH = 1.0
    SUMMARY -> AttributeCreator_4
    SUMMARY -> FeatureHolder_3

Bookmark: PDF rapport
Note: Zorgt dat bij OUTPUT = beide, maar 1 mail gestuurd word
AttributeManager_2
    ATTR_TABLE:
      REMOVE Wijk
      RENAME_SET_VALUE Oppervlak > Oppervlak_m2
    -> TableAdder

Bookmark: Tabel
TableAdder
    MINXVALATTR = 100
    MAXXVALATTR = 500
    HEIGHT = 18
    ChartTitle = Oppervlak per Type
    HEIGHT_2 = 10
    MAXYVALATTR = 10
    ATTRLIST = Type Oppervlak_m2 Percentage
    Outline -> PDFStyler
    Text -> TestFilter_2
PDFStyler
    LINE_WIDTH = 1.0
    COLOR = 0,0,0
    OPACITY = 1.0
    LINE_JOIN_STYLE_PARAM = Miter Join
    LINE_DASH_PHASE = 0
    LINE_MITER_LIMIT = 0.0
    FILL_OPACITY = 0.00
    FILL_COLOR = 0,0,0
    LINE_CAP_STYLE_PARAM = Butt Cap
    FONT = Arial
    PDFStyled -> AttributeCreator_2
AttributeCreator_2
    ATTR_TABLE = SET_TO SORT = 2
    -> Sorter
TestFilter_2
    TEST_LIST = BOOL_OP,OR,COMPOSITE_TEST,<Unused>,TEST_CLAUSE,"TEST @Value(Font) = Arial,18",@Value(Font) = Arial,18,BOOL_OP,OR,COMPOSITE_TEST,<Unused>,TEST_CLAUSE,"TEST @Value(Label) = Oppervlak",@Value(Label) = Oppervlak,BOOL_OP,OR,COMPOSITE_TEST,<Unused>,TEST_CLAUSE,"TEST @Value(Font) = Arial,10",@Value(Font) = Arial,10
    DEFAULT_VALUE = <UNFILTERED>
    @Value(Font) = Arial,18 -> PDFStyler_3
    @Value(Font) = Arial,10 -> PDFStyler_2
PDFStyler_3
    LINE_WIDTH = 1.0
    COLOR = 0,0,0
    OPACITY = 1.0
    LINE_JOIN_STYLE_PARAM = Miter Join
    LINE_DASH_PHASE = 0
    LINE_MITER_LIMIT = 0.0
    FILL_OPACITY = 1.00
    FILL_COLOR = 0,0,0
    LINE_CAP_STYLE_PARAM = Butt Cap
    FONT = MS Sans Serif,18
    PDFStyled -> AttributeCreator
PDFStyler_2
    LINE_WIDTH = 1.0
    COLOR = 0,0,0
    OPACITY = 1.0
    LINE_JOIN_STYLE_PARAM = Miter Join
    LINE_DASH_PHASE = 0
    LINE_MITER_LIMIT = 0.0
    FILL_OPACITY = 1.00
    FILL_COLOR = 0,0,0
    LINE_CAP_STYLE_PARAM = Butt Cap
    FONT = MS Sans Serif,10
    PDFStyled -> AttributeCreator
AttributeCreator
    ATTR_TABLE = SET_TO SORT = 1
    -> Sorter
Sorter
    SORT_PARM = SORT ALPHA ASCENDING
    SORTED -> PDFPageFormatter [HTML TABLE]

Bookmark: Wijk opp berekenen
Aggregator_16
    AGGREGATE_TYPE = Homogeneous Collection (If Possible)
    ORDERED = No
    ACCUM_ATTRS_NAME = Get Attributes From One Representative Feature
    SEP = ,
    MODE = Geometry - Assemble One Level
    GROUP_BY = Type Wijk
    AGGREGATE -> AreaCalculator_8
AreaCalculator_8
    AREA_TYPE = Plane Area
    AREA_ATTR = Oppervlak
    MULT = 1
    -> AttributeRounder_8
AttributeRounder_8
    PLACES = 2
    ROUND_TYPE = Nearest
    SRC_ATTRS = Oppervlak
    -> Sorter_2
Sorter_2
    SORT_PARM = Wijk ALPHA ASCENDING Type ALPHA ASCENDING
    SORTED -> Tester_2

Bookmark: Excel writer
FeatureWriter
    XLSXW_RASTER_FORMAT = PNG
    XLSXW_TEMPLATE_SHEET = Totaal
    DATASET = $(FME_MF_DIR_ENCODED)producten\oppervlak_download.xlsx
    FORMAT = XLSXW
    WRITER_DIRECTIVES = OVERWRITE_FILE,No,WRITER_MODE,Insert,TEMPLATEFILE,$(FME_MF_DIR$encode)templates\oppervlak_download_template.xlsx,RASTER_FORMAT,PNG,TRUNCATE_TABLE,No,DESTINATION_DATASETTYPE_VALIDATION,Yes,TEMPLATE_SHEET,Totaal,DROP_TABLE,No,FIELD_NAMES_OUT,No
    XLSXW_FIELD_NAMES_OUT = No
    XLSXW_TRUNCATE_TABLE = No
    XLSXW_DESTINATION_DATASETTYPE_VALIDATION = Yes
    XLSXW_DROP_TABLE = No
    XLSXW_OVERWRITE_FILE = No
    FEATURE_TYPE_LIST_ATTR = _feature_type
    XLSXW_WRITER_MODE = Insert
    XLSXW_TEMPLATEFILE = $(FME_MF_DIR)templates\oppervlak_download_template.xlsx
    DATASET_ATTR = _dataset
    TOTAL_FEATURES_WRITTEN_ATTR = _total_features_written
    SUMMARY -> FeatureHolder_2
    SUMMARY -> ZipArchiver_2

Bookmark: Mailer
Tester_4
    TEST_DESCRIPTION = ""
    TEST_CLAUSE = TEST @Value(_dataset) ATTRIBUTE_HAS_VALUE ""
    BOOL_OP = OR
    TEST_MODE = Automatic
    PASSED -> TestFilter_7
TestFilter_7
    TEST_LIST = BOOL_OP,OR,COMPOSITE_TEST,<Unused>,TEST_CLAUSE,"TEST $(OUTPUT_TYPE) = pdf",__OUTPUT_TYPE_ = pdf,BOOL_OP,OR,COMPOSITE_TEST,<Unused>,TEST_CLAUSE,"TEST $(OUTPUT_TYPE) = excel",__OUTPUT_TYPE_ = excel,BOOL_OP,OR,COMPOSITE_TEST,<Unused>,TEST_CLAUSE,"TEST $(OUTPUT_TYPE) = beide",__OUTPUT_TYPE_ = beide
    DEFAULT_VALUE = <UNFILTERED>
    __OUTPUT_TYPE_ = pdf -> StringConcatenator
    __OUTPUT_TYPE_ = excel -> StringConcatenator_2
    __OUTPUT_TYPE_ = beide -> StringConcatenator_3
StringConcatenator
    PARM_LINE:
      Hallo,

      Hierbij ontvangt u de oppervlaktes binnen de wijk(en) $(WIJKEN_SELECT). Mocht u nog vragen hebben kunt u ons mailen op geo-informatie@nieuwegein.nl

      Met vriendelijke groet,

      Team Geo-Informatie
    ACTION = Create New Attribute
    VAL_ATTR = _result
    -> PythonEmailer [TRIGGER]
StringConcatenator_2
    PARM_LINE:
      Hallo,

      Hierbij ontvangt u de oppervlaktes binnen de wijk(en) $(WIJKEN_SELECT). Mocht u nog vragen hebben kunt u ons mailen op geo-informatie@nieuwegein.nl

      Met vriendelijke groet,

      Team Geo-Informatie
    ACTION = Create New Attribute
    VAL_ATTR = _result
    -> PythonEmailer [TRIGGER]
PythonEmailer
    email_server = "smtp.nieuwegein.nl "
    server_port = 25
    email_subject = Opgevraagde oppervlaktes
    email_message = @Value(_result)
    email_message_type = plain
    email_to = $(EMAIL)
    cType = TLS
    attachments = @Value(_dataset)
    email_from = geo-informatie@nieuwegein.nl
StringConcatenator_3
    PARM_LINE:
      Hallo,

      Hierbij ontvangt u de oppervlaktes binnen de wijk(en) $(WIJKEN_SELECT). Mocht u nog vragen hebben kunt u ons mailen op geo-informatie@nieuwegein.nl

      Met vriendelijke groet,

      Team Geo-Informatie
    ACTION = Create New Attribute
    VAL_ATTR = mail_tekst
    -> Tester_5
Tester_5
    TEST_DESCRIPTION = ""
    TEST_CLAUSE = TEST @Value(mail_pass) = 1
    BOOL_OP = OR
    TEST_MODE = Automatic
    PASSED -> PythonEmailer_2 [TRIGGER]
PythonEmailer_2
    email_server = "smtp.nieuwegein.nl "
    server_port = 25
    email_subject = Opgevraagde oppervlaktes
    email_message = @Value(mail_tekst)
    email_message_type = plain
    email_to = $(EMAIL)
    cType = TLS
    attachments = $(FME_MF_DIR)producten\oppervlak_download.zip
    email_from = geo-informatie@nieuwegein.nl

Bookmark: Mail adres tester
Note: Alleen @nieuwegein.nl adressen worden doorgelaten
Tester_3
    TEST_DESCRIPTION = ""
    TEST_CLAUSE = TEST $(EMAIL) LIKE %@nieuwegein.nl
    BOOL_OP = OR
    TEST_MODE = Automatic
    FAILED -> Terminator
Terminator
    MESSAGE = Translation Terminated

FME custom transformer BGT Object selector

Wijken (input)
    -> Wijken_-__Clipper_CLIPPER
    -> FeatureReader_3 [INITIATOR]
Wijken_-__Clipper_CLIPPER: Junction
    -> Clipper [CLIPPER]
    -> Clipper_3 [CLIPPER]
    -> Clipper_4 [CLIPPER]
    -> Clipper_2 [CLIPPER]
    -> Clipper_7 [CLIPPER]
    -> Clipper_5 [CLIPPER]
    -> Clipper_8 [CLIPPER]
    -> Clipper_6 [CLIPPER]
FeatureReader_3
    ATTR_ACCUM_MODE = Only Use Result
    ORACLE_SPATIAL_USE_SEARCH_ENVELOPE = NO
    ORACLE_SPATIAL_USE_UNIFIED_DATE_ATTRS = YES
    ORACLE_SPATIAL_READ_3D_POLYGON_AS_FACE = NO
    INTERACT = Intersects
    ORACLE_SPATIAL_PARSE_MAPINFO_SYMBOLOGY = NO
    ORACLE_SPATIAL_CLIP_TO_ENVELOPE = NO
    WHERE = BGTSTATUS LIKE 'bestaand' AND RELATIEVEHOOGTELIGGING = 0
    COORDSYS = EPSG:28992
    ORACLE_SPATIAL_CHUNK_SIZE = 200
    FEATURETYPES = IMGEO.BEGROEIDTERREINDEEL IMGEO.KUNSTWERKDEEL IMGEO.ONBEGROEIDTERREINDEEL IMGEO.ONDERSTEUNENDWATERDEEL IMGEO.ONDERSTEUNENDWEGDEEL IMGEO.OVERBRUGGINGSDEEL IMGEO.OVERIGBOUWWERK IMGEO.PAND IMGEO.SCHEIDING IMGEO.WATERDEEL IMGEO.WEGDEEL
    COMBINE_GEOM = Use Result
    ORACLE_SPATIAL_PASSWORD =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
    ORACLE_SPATIAL_QUERY_FEATURE_TYPES_FOR_MERGE_FILTERS = Yes
    OUTPUT_FEATURES_DISPLAY = Schema and Data Features
    ORACLE_SPATIAL_USER_NAME = IMGEO
    ORACLE_SPATIAL_REMOVE_SCHEMA_QUALIFIER = NO
    ORACLE_SPATIAL_SERVER_TYPE = ORACLE8i
    ORACLE_SPATIAL_PERSISTENT_CONNECTION = YES
    ORACLE_SPATIAL_INTERRESULT = = 'TRUE'
    DATASET = VNGP
    ORACLE_SPATIAL_HANDLE_MULTIPLE_SPATIAL_COLUMNS = NO
    ORACLE_SPATIAL_INTERACTION = ANYINTERACT
    FORMAT = ORACLE_SPATIAL
    ATTRIBUTES = IMGEO.BEGROEIDTERREINDEEL,"IDENTIFICATIE,OBJECTBEGINTIJD,OBJECTEINDTIJD,TIJDSTIPREGISTRATIE,EINDREGISTRATIE,LV_PUBLICATIEDATUM,BRONHOUDER,BGTSTATUS,PLUSSTATUS,INONDERZOEK,BEGROEIDTERREINDEELOPTALUD,RELATIEVEHOOGTELIGGING,BGTFYSIEKVOORKOMEN,PLUSFYSIEKVOORKOMEN,SYS_FILTEREN,BOR_ID,XFM_ID,BORBEHEERDER,CUSTOMFYSIEKVOORKOMEN",IMGEO.KUNSTWERKDEEL,"IDENTIFICATIE,OBJECTBEGINTIJD,OBJECTEINDTIJD,TIJDSTIPREGISTRATIE,EINDREGISTRATIE,LV_PUBLICATIEDATUM,BRONHOUDER,BGTSTATUS,PLUSSTATUS,INONDERZOEK,RELATIEVEHOOGTELIGGING,BGTTYPE,PLUSTYPE,SYS_FILTEREN,BOR_ID,XFM_ID,BORBEHEERDER,CUSTOMTYPE",IMGEO.ONBEGROEIDTERREINDEEL,"IDENTIFICATIE,OBJECTBEGINTIJD,OBJECTEINDTIJD,TIJDSTIPREGISTRATIE,EINDREGISTRATIE,LV_PUBLICATIEDATUM,BRONHOUDER,BGTSTATUS,PLUSSTATUS,INONDERZOEK,ONBEGROEIDTERREINDEELOPTALUD,RELATIEVEHOOGTELIGGING,BGTFYSIEKVOORKOMEN,PLUSFYSIEKVOORKOMEN,SYS_FILTEREN,BOR_ID,XFM_ID,BORBEHEERDER,CUSTOMFYSIEKVOORKOMEN",IMGEO.ONDERSTEUNENDWATERDEEL,"IDENTIFICATIE,OBJECTBEGINTIJD,OBJECTEINDTIJD,TIJDSTIPREGISTRATIE,EINDREGISTRATIE,LV_PUBLICATIEDATUM,BRONHOUDER,BGTSTATUS,PLUSSTATUS,INONDERZOEK,DROOGVALLEND,RELATIEVEHOOGTELIGGING,BGTTYPE,PLUSTYPE,SYS_FILTEREN,BOR_ID,XFM_ID,BORBEHEERDER,CUSTOMTYPE",IMGEO.ONDERSTEUNENDWEGDEEL,"IDENTIFICATIE,OBJECTBEGINTIJD,OBJECTEINDTIJD,TIJDSTIPREGISTRATIE,EINDREGISTRATIE,LV_PUBLICATIEDATUM,BRONHOUDER,BGTSTATUS,PLUSSTATUS,INONDERZOEK,ONDERSTEUNENDWEGDEELOPTALUD,RELATIEVEHOOGTELIGGING,BGTFUNCTIE,PLUSFUNCTIE,BGTFYSIEKVOORKOMEN,PLUSFYSIEKVOORKOMEN,SYS_FILTEREN,BOR_ID,XFM_ID,BORBEHEERDER,CUSTOMFUNCTIE,CUSTOMFYSIEKVOORKOMEN",IMGEO.OVERBRUGGINGSDEEL,"IDENTIFICATIE,OBJECTBEGINTIJD,OBJECTEINDTIJD,TIJDSTIPREGISTRATIE,EINDREGISTRATIE,LV_PUBLICATIEDATUM,BRONHOUDER,BGTSTATUS,PLUSSTATUS,INONDERZOEK,OVERBRUGGINGISBEWEEGBAAR,RELATIEVEHOOGTELIGGING,TYPEOVERBRUGGINGSDEEL,HOORTBIJTYPEOVERBRUGGING,SYS_FILTEREN,BOR_ID,XFM_ID,BORBEHEERDER,CUSTOMTYPEOVERBRUGGINGSDEEL,CUSTOMHOORTBIJTYPEOVERBRUGGING",IMGEO.OVERIGBOUWWERK,"IDENTIFICATIE,OBJECTBEGINTIJD,OBJECTEINDTIJD,TIJDSTIPREGISTRATIE,EINDREGISTRATIE,LV_PUBLICATIEDATUM,BRONHOUDER,BGTSTATUS,PLUSSTATUS,INONDERZOEK,RELATIEVEHOOGTELIGGING,BGTTYPE,PLUSTYPE,SYS_FILTEREN,BOR_ID,XFM_ID,BORBEHEERDER,CUSTOMTYPE",IMGEO.PAND,"IDENTIFICATIE,OBJECTBEGINTIJD,OBJECTEINDTIJD,TIJDSTIPREGISTRATIE,EINDREGISTRATIE,LV_PUBLICATIEDATUM,BRONHOUDER,BGTSTATUS,PLUSSTATUS,INONDERZOEK,RELATIEVEHOOGTELIGGING,IDENTIFICATIEBAGPND,NUMAANDUIDINGVISUALISATIE,SYS_FILTEREN,BOR_ID,XFM_ID,BORBEHEERDER",IMGEO.SCHEIDING,"IDENTIFICATIE,OBJECTBEGINTIJD,OBJECTEINDTIJD,TIJDSTIPREGISTRATIE,EINDREGISTRATIE,LV_PUBLICATIEDATUM,BRONHOUDER,BGTSTATUS,PLUSSTATUS,INONDERZOEK,RELATIEVEHOOGTELIGGING,BGTTYPE,PLUSTYPE,SYS_FILTEREN,BOR_ID,XFM_ID,BORBEHEERDER,CUSTOMTYPE",IMGEO.WATERDEEL,"IDENTIFICATIE,OBJECTBEGINTIJD,OBJECTEINDTIJD,TIJDSTIPREGISTRATIE,EINDREGISTRATIE,LV_PUBLICATIEDATUM,BRONHOUDER,BGTSTATUS,PLUSSTATUS,INONDERZOEK,DROOGVALLEND,RELATIEVEHOOGTELIGGING,BGTTYPE,PLUSTYPE,SYS_FILTEREN,BOR_ID,XFM_ID,BORBEHEERDER,CUSTOMTYPE",IMGEO.WEGDEEL,"IDENTIFICATIE,OBJECTBEGINTIJD,OBJECTEINDTIJD,TIJDSTIPREGISTRATIE,EINDREGISTRATIE,LV_PUBLICATIEDATUM,BRONHOUDER,BGTSTATUS,PLUSSTATUS,INONDERZOEK,WEGDEELOPTALUD,RELATIEVEHOOGTELIGGING,BGTFUNCTIE,PLUSFUNCTIE,BGTFYSIEKVOORKOMEN,PLUSFYSIEKVOORKOMEN,SYS_FILTEREN,BOR_ID,XFM_ID,BORBEHEERDER,CUSTOMFUNCTIE,CUSTOMFYSIEKVOORKOMEN"
    ORACLE_SPATIAL_SHOW_SYSTEM_TABLES = NO
    IMGEO.BEGROEIDTERREINDEEL -> Clipper [CLIPPEE]
    IMGEO.KUNSTWERKDEEL -> Clipper_2 [CLIPPEE]
    IMGEO.ONBEGROEIDTERREINDEEL -> Clipper_3 [CLIPPEE]
    IMGEO.ONDERSTEUNENDWATERDEEL -> Clipper_4 [CLIPPEE]
    IMGEO.ONDERSTEUNENDWEGDEEL -> Clipper_5 [CLIPPEE]
    IMGEO.OVERBRUGGINGSDEEL -> Clipper_6 [CLIPPEE]
    IMGEO.OVERIGBOUWWERK -> Clipper_2 [CLIPPEE]
    IMGEO.PAND -> Clipper_2 [CLIPPEE]
    IMGEO.SCHEIDING -> Clipper_2 [CLIPPEE]
    IMGEO.WATERDEEL -> Clipper_7 [CLIPPEE]
    IMGEO.WEGDEEL -> Clipper_8 [CLIPPEE]
Clipper
    PRESERVE_CLIPPEE_EXTENTS = No
    CLIP_TYPE = Multiple Clippers
    CLIPPED_ATTR = _clipped
    CREATE_AGGREGATES = Yes
    BOUNDARY_CASES = Treat as Inside
    ATTR_ACCUM_MODE = Prefix Clipper
    CONNECT_Z_MODE = First Wins
    LINES_AS_SEGMENTS = No
    CLIPPER_PREFIX = wijken_
    INSIDE -> Begroeidterreindeel (output)
Begroeidterreindeel (output)
Clipper_2
    PRESERVE_CLIPPEE_EXTENTS = No
    CLIP_TYPE = Multiple Clippers
    CLIPPED_ATTR = _clipped
    CREATE_AGGREGATES = Yes
    BOUNDARY_CASES = Treat as Inside
    ATTR_ACCUM_MODE = Prefix Clipper
    CONNECT_Z_MODE = First Wins
    LINES_AS_SEGMENTS = No
    CLIPPER_PREFIX = wijken_
    INSIDE -> Bebouwd (output)
Bebouwd (output)
Clipper_3
    PRESERVE_CLIPPEE_EXTENTS = No
    CLIP_TYPE = Multiple Clippers
    CLIPPED_ATTR = _clipped
    CREATE_AGGREGATES = Yes
    BOUNDARY_CASES = Treat as Inside
    ATTR_ACCUM_MODE = Prefix Clipper
    CONNECT_Z_MODE = First Wins
    LINES_AS_SEGMENTS = No
    CLIPPER_PREFIX = wijken_
    INSIDE -> Onbegroeidterreindeel (output)
Onbegroeidterreindeel (output)
Clipper_7
    PRESERVE_CLIPPEE_EXTENTS = No
    CLIP_TYPE = Multiple Clippers
    CLIPPED_ATTR = _clipped
    CREATE_AGGREGATES = Yes
    BOUNDARY_CASES = Treat as Inside
    ATTR_ACCUM_MODE = Prefix Clipper
    CONNECT_Z_MODE = First Wins
    LINES_AS_SEGMENTS = No
    CLIPPER_PREFIX = wijken_
    INSIDE -> Waterdeel (output)
Waterdeel (output)
Clipper_4
    PRESERVE_CLIPPEE_EXTENTS = No
    CLIP_TYPE = Multiple Clippers
    CLIPPED_ATTR = _clipped
    CREATE_AGGREGATES = Yes
    BOUNDARY_CASES = Treat as Inside
    ATTR_ACCUM_MODE = Prefix Clipper
    CONNECT_Z_MODE = First Wins
    LINES_AS_SEGMENTS = No
    CLIPPER_PREFIX = wijken_
    INSIDE -> Ondersteunend_Waterdeel (output)
Ondersteunend_Waterdeel (output)
Clipper_5
    PRESERVE_CLIPPEE_EXTENTS = No
    CLIP_TYPE = Multiple Clippers
    CLIPPED_ATTR = _clipped
    CREATE_AGGREGATES = Yes
    BOUNDARY_CASES = Treat as Inside
    ATTR_ACCUM_MODE = Prefix Clipper
    CONNECT_Z_MODE = First Wins
    LINES_AS_SEGMENTS = No
    CLIPPER_PREFIX = wijken_
    INSIDE -> Ondersteunend_wegdeel (output)
Ondersteunend_wegdeel (output)
Clipper_6
    PRESERVE_CLIPPEE_EXTENTS = No
    CLIP_TYPE = Multiple Clippers
    CLIPPED_ATTR = _clipped
    CREATE_AGGREGATES = Yes
    BOUNDARY_CASES = Treat as Inside
    ATTR_ACCUM_MODE = Prefix Clipper
    CONNECT_Z_MODE = First Wins
    LINES_AS_SEGMENTS = No
    CLIPPER_PREFIX = wijken_
    INSIDE -> Overbruggingsdeel (output)
Overbruggingsdeel (output)
Clipper_8
    PRESERVE_CLIPPEE_EXTENTS = No
    CLIP_TYPE = Multiple Clippers
    CLIPPED_ATTR = _clipped
    CREATE_AGGREGATES = Yes
    BOUNDARY_CASES = Treat as Inside
    ATTR_ACCUM_MODE = Prefix Clipper
    CONNECT_Z_MODE = First Wins
    LINES_AS_SEGMENTS = No
    CLIPPER_PREFIX = wijken_
    INSIDE -> Wegdeel (output)
Wegdeel (output)

FME custom transformer TextBoxAdder

Parameters:
- MINXVALATTR =   # Min X Value
- MINYVALATTR =   # Min Y Value
- MAXXVALATTR =   # Max X Value
- MAXYVALATTR =   # Max Y Value
- HEIGHT = 18   # Label Height
- LabelText =   # Label Text

INPUT (input)
    -> 2DBoxReplacer
Box (output)
Text (output)

Bookmark: Create Box
2DBoxReplacer
    MINXVALATTR = $(MINXVALATTR)
    MINYVALATTR = $(MINYVALATTR)
    MAXXVALATTR = $(MAXXVALATTR)
    MAXYVALATTR = $(MAXYVALATTR)
    BOX -> CenterPointReplacer_2
    BOX -> Box (output)

Bookmark: Add Label
CenterPointReplacer_2
    CENTERPOINT -> CoordinateExtractor_2
CoordinateExtractor_2
    Z_DEFAULT = -9999
    Z_ATTR = _z
    Y_ATTR = _y
    IND = 0
    X_ATTR = _x
    -> AttributeCreator
AttributeCreator
    ATTR_LIST = Font,Arial,$(HEIGHT),Label,$(LabelText)
    -> LabelPointReplacer_2
LabelPointReplacer_2
    LABATTR = Label
    HEIGHT = $(HEIGHT)
    ALWAYSROTATE = no
    LABELPOINT -> BoundingBoxReplacer

Bookmark: Center Justify Label
BoundingBoxReplacer
    BOXTYPE = Bounding Box
    BOX -> CenterPointReplacer
CenterPointReplacer
    CENTERPOINT -> CoordinateExtractor
CoordinateExtractor
    Z_DEFAULT = -9999
    Z_ATTR = _zt
    Y_ATTR = _yt
    IND = 0
    X_ATTR = _xt
    -> 2DPointReplacer
2DPointReplacer
    XVALATTR = @Value(_x)-(@Value(_xt)-@Value(_x))
    YVALATTR = @Value(_y)-(@Value(_yt)-@Value(_y))
    POINT -> LabelPointReplacer
LabelPointReplacer
    LABATTR = Label
    HEIGHT = $(HEIGHT)
    ALWAYSROTATE = yes
    LABELPOINT -> Text (output)

FME custom transformer ZipArchiver
Compresses a file or folder and appends it into the specified zip file.
    The archive name will be the same as the target file name. If a file having the same name as the target file has been archived in the zip file already, the file will not be archived.
    The transformer creates a new zip file when receiving the first file that should be archived into it, if the specified zip file doesn't exist. 
    -----
    Note: This transformer has been basically internationalized with 2016-01-22 update. However, depending on the environment (platform, OS version etc.), file path strings containing Non-ASCII characters still may not be treated correctly. Please test enough if the path strings may contain Non-ASCII characters.
    -----
    Input features will be output through the Output port as-is.
    The transformer creates log features which contain these attributes for each file, and outputs them from the LogSuccess/LogFailure port.
    - Result: "success" if the file was archived successfully, "failure" otherwise.
    - Target File: the target file path.
    - Zip File: the zip file path.
    - Archive Name: the archive name of the target file in the zip file if archived successfully, empty otherwise.
    - Comment: compression ratio if archived successfully, failure reason otherwise.
    ファイルまたはフォルダを圧縮し、指定したzipファイルに追加します。
    アーカイブ名は対象のファイル名と同じになります。対象とするファイルと同じ名前のファイルがすでにzipファイルにアーカイブされていた場合、そのファイルはアーカイブされません。
    指定したzipファイルが存在しない場合、このトランスフォーマーはそれにアーカイブすべき最初のファイルを受け取ったときに新しいzipファイルを作成します。
-----
    注: 2016-01-22 の更新によって、このトランスフォーマーは基本的には国際化されました。しかし、環境（プラットフォームやOSのバージョンなど）によっては、ASCII文字（半角の英数字や記号）以外の文字を含むファイルパス文字列ま、まだ正しく処理されない可能性があります。パス文字列に非ASCII文字が含まれる可能性がある場合は、十分にテストしてください。
-----
    入力フィーチャーはそのままOutputポートから出力されます。
    このトランスフォーマーは、次の属性を持つログフィーチャーをファイルごとに作成し、LogSuccess/LogFailureポートから出力します。
    - Result: ファイルが正常にアーカイブされた場合は"succcess"、そうでない場合は"failure"
    - Target File: 対象のファイルパス
    - Zip File: zipファイルパス
    - Archive Name: アーカイブに成功した場合はzipファイル内でのアーカイブ名、失敗した場合は空文字列
    - Comment: アーカイブに成功した場合は圧縮率、失敗した場合はその理由
Parameters 
    Target File or Folder
    : 
    Specify a file or folder path that should be archived. You can also set a feature attribute value to this parameter.
    If you specify a folder path here, all files under the folder will be archived. In the case, the original directory structure will also be preserved, and the archive name of the file will contain path starting from the specified folder.
    アーカイブするファイルまたはフォルダのパスを指定します。フィーチャーの属性をこのパラメーターに設定することもできます。 
    ここにフォルダのパスを指定した場合は、そのフォルダ以下にある全てのファイルがアーカイブされます。その場合、元のディレクトリ構造も維持され、ファイルのアーカイブ名には、指定されたフォルダから始まるパスが含まれます。
    Destination Zip File
    : 
    Specify a zip file path (*.zip). You can also set a feature attribute value to this parameter.
    If the extension of the specified file path is not "zip", the transformer will add ".zip" to the path automatically. 
    zipファイルパス（*.zip）を指定します。フィーチャーの属性をこのパラメーターに設定することもできます。 
    指定されたパスの拡張子が"zip"でない場合は、そのパスに".zip"を自動的に付加します。
    If Destination Zip File Exists
    :
    If the specified destination zip file exists at the translation starting time, this transformer appends compressed files into the existing zip file, by default. If you set 
    "Remove Existing Zip File"
    to this parameter, this transformer removes the existing zip file once at first, and then appends compressed files into the newly created same name zip file. If you set 
    "Rename Destination Zip File"
    , an suffix will be added to the destination zip file name automatically to differentiate from the existing zip file.
    変換の開始時に指定されたzipファイルが存在する場合、デフォルトでは、このトランスフォーマーは既存のzipファイルに圧縮したファイルを追加します。このパラメーターに 
    "Remove Existing Zip File"
    を設定した場合は、このトランスフォーマーは最初に一回だけ既存のzipファイルを削除してから、新たに作成した同じ名前のzipファイルに圧縮したファイルを追加します。
    "Rename Destination Zip File"
    を設定した場合は、既存のzipファイルと区別するため、出力先のzipファイル名にサフィクスが自動的に付加されます。
Copyright (c) 2015-2016 pragmatica inc. 
    Permission is granted to anyone, free of charge, to use, modify and distribute the object code form of this transformer for any purpose, subject to the following restrictions: 
    1) The origin of this transformer and associated FME(R) software must not be misrepresented. 
    2) This transformer may only be used in conjunction with a validly licensed copy of FME software. 
    THIS SOFTWARE IS PROVIDED BY PRAGMATICA INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL PRAGMATICA INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- FILE_PATH =   # Target File or Folder
- ZIP_PATH =   # Destination Zip File
- MODE = APPEND

Input (input)
    -> ParameterFetcher
ParameterFetcher
    ATTR_LIST = __ziparchiver.filepath {$(FILE_PATH)} __ziparchiver.zippath {$(ZIP_PATH)} __ziparchiver.mode {$(MODE)}
    -> PythonCaller
PythonCaller
    PYTHONSYMBOL = ZipArchiver
    PYTHONSOURCE:
      import fme
      import fmeobjects
      import os, zipfile, locale

      # 2015-05-24  Takashi Iijima  Original Implementation
      # 2016-01-22  Takashi Iijima  Refactoring and Internationalizing (Tech Preview)

      class ZipArchiver(object):
          def __init__(self):
              t = locale.getdefaultlocale()
              self.encode = lambda s: (s.encode(t[1]) if t else s) if isinstance(s, unicode) else s
              self.logger = fmeobjects.FMELogFile()
              self.zpaths = {} # key: specified zip file path (lower-case), value: treated zip file path in this session

          def input(self, feature):
              try:
                  # Retrieve target file path and zip file path from feature attributes.
                  # If the specified zip file path doesn't end with ".zip", add the extension.
                  regulatePath = lambda path: os.path.abspath(path).replace('\\', '/')
                  fpath = regulatePath(feature.getAttribute('__ziparchiver.filepath'))
                  zpath = regulatePath(feature.getAttribute('__ziparchiver.zippath'))
                  if not zpath.lower().endswith('.zip'):
                      zpath = '%s.zip' % zpath
                  keyPath = zpath.lower()

                  mode = feature.getAttribute('__ziparchiver.mode')
                  if os.path.exists(zpath):
                      if mode == 'REMOVE':
                          if keyPath not in self.zpaths:
                              os.remove(zpath)
                      elif mode == 'RENAME':
                          if keyPath in self.zpaths:
                              zpath = self.zpaths[keyPath]
                          else:
                              format, n = '%s_%d.zip', 1
                              while os.path.exists(format % (zpath[:-4], n)): n += 1
                              zpath = format % (zpath[:-4], n)
                  self.zpaths[keyPath] = zpath

                  # Collect  target file paths, including empty directries if "fpath" is a directory.
                  # If specifid file/directory doesn't exist, throw an error.
                  root = ''
                  fpaths, dpaths = [], []
                  if os.path.exists(fpath): # fpath is a file
                      root = os.path.split(fpath)[0]
                      if os.path.isfile(fpath):
                          fpaths = [fpath]
                      elif os.listdir(fpath): # fpath is a non-empty directory
                          for dirpath, dirnames, filenames in os.walk(fpath):
                              paths = [os.path.join(dirpath, d) for d in dirnames]
                              dpaths += [regulatePath(path) for path in paths if not os.listdir(path)]
                              fpaths += [regulatePath(os.path.join(dirpath, f)) for f in filenames]
                      else: # fpath is an empty directory
                          dpaths = [fpath]
                  else:
                      raise Exception('specified file doesn\'t exist.')

                  # If destination directory doesn't exist, create the directory.
                  if not os.path.exists(os.path.split(zpath)[0]):
                      os.makedirs(os.path.split(zpath)[0])

                  # Then, perform archiving.
                  with zipfile.ZipFile(zpath, 'a', zipfile.ZIP_DEFLATED) as zipper:
                      for path in [path for path in fpaths if path.lower() != zpath.lower()]:
                          aname = path[len(root) + 1:] # archive name
                          result, msg = False, ''
                          try:
                              info = zipper.getinfo(aname)
                              msg = '"%s" exists in the archive already.' % aname
                          except:
                              try:
                                  zipper.write(path, aname)
                                  info = zipper.getinfo(aname)
                                  after = info.compress_size/1024.0
                                  before = info.file_size/1024.0
                                  msg = '%.1f%% (%.1f/%.1fKB)' % (after/before*100.0, after, before)
                                  result = True
                              except Exception as ex:
                                  msg = '%s' % ex
                          self.outputLogFeature('Success' if result else 'Failure', path, zpath, aname, msg)
                      for path in dpaths:
                          aname = path[len(root) + 1:] # archive name
                          try:
                              info = zipper.getinfo(aname)
                          except:
                              zipper.write(path, aname)
              except Exception as ex:
                  self.outputLogFeature('Terminate', fpath, zpath, '', '%s' % ex)
              finally: # always output the input feature through the Output port.
                  self.pyoutput(feature)

          # Output a log feature.
          def outputLogFeature(self, flag, fpath, zpath, aname, msg):
              if flag != 'Success':
                  self.logger.logMessageString(self.encode('ZipArchiver: %s' % msg), \
                      fmeobjects.FME_ERROR if flag == 'Terminate' else fmeobjects.FME_WARN)
              feature = fmeobjects.FMEFeature()
              feature.setAttribute('__ziparchiver.result', flag.lower())
              feature.setAttribute('Target File', fpath)
              feature.setAttribute('Zip File', zpath)
              feature.setAttribute('Archive Name', aname if flag == 'Success' else '')
              feature.setAttribute('Comment', msg)
              feature.setAttribute('fme_feature_type', 'ZipArchiver_%s' % flag)
              self.pyoutput(feature)
    NEW_ATTRIBUTES = __ziparchiver.result
    -> Tester
Tester
    TEST_DESCRIPTION = ""
    TEST_CLAUSE = TEST __ziparchiver.result ATTRIBUTE_IS_MISSING ""
    BOOL_OP = OR
    TEST_MODE = Automatic
    PASSED -> Output (output)
    FAILED -> AttributeRenamer
Output (output)
AttributeRenamer
    ATTR_LIST = __ziparchiver.result,Result,
    -> AttributeExposer
AttributeExposer
    ATTR_LIST = "Target File","Zip File","Archive Name",Comment
    -> AttributeKeeper
AttributeKeeper
    KEEP_ATTRS = Archive Name,Comment,Result,Target File,Zip File
    -> AttributeFilter
AttributeFilter
    ATTR_VALUES = success,failure,terminate,<EMPTY>,<MISSING>,<NULL>,<UNFILTERED>
    ATTR_NAME = Result
    success -> LogSuccess (output)
    failure -> LogFailure (output)
    terminate -> Terminator
LogSuccess (output)
LogFailure (output)
Terminator
    MESSAGE = @Value(Comment)

FME custom transformer TableAdder
Generates a vector-based table of attribute data for writing to pdf or other vector formats
Users specify the minimum and maximum coordinates of the table as well as the maximum y coordinate. Attributes to be summarized are selected. A table name can also be given. The length of the table will depend on the number of attributes and the font size specified. Table text and boundaries can be later styled with other styler transformers such as the PDF Styler.
Copyright (c) 2013 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- FME_PROCESS_GROUP_BY =   # " " Group By
- ChartTitle = Title   # Chart Title
- MINXVALATTR =   # Min X Value
- MAXXVALATTR =   # Max X Value
- MAXYVALATTR =   # Max Y Value
- HEIGHT = 18   # Title Height
- HEIGHT_2 = 12   # Row Text Height
- ATTRLIST =   # Selected Attributes

INPUT (input)
    -> TextBoxAdder_2
    -> ParameterFetcher
Outline (output)
Text (output)

Bookmark: Add Title
TextBoxAdder_2
    MINXVALATTR = $(MINXVALATTR)
    MINYVALATTR = $(MAXYVALATTR)-$(HEIGHT)*2
    MAXXVALATTR = $(MAXXVALATTR)
    HEIGHT = $(HEIGHT)
    MAXYVALATTR = $(MAXYVALATTR)
    LabelText = $(ChartTitle)
    Box -> AttributeRemover_2
    Text -> AttributeRemover

Bookmark: Calculate Number of Columns
ParameterFetcher
    ATTR_LIST = _ATTRLIST {$(ATTRLIST)}
    -> AttributeSplitter
AttributeSplitter
    ATTR_NAME = _ATTRLIST
    TRIM_OPTION = Both
    DROP_EMPTY_PARTS = No
    DELIMITER = " "
    LIST_NAME = _list
    -> ListElementCounter
ListElementCounter
    CNT_ATTR = AttributeCount
    LIST_NAME = _list{}
    -> Counter_5

Bookmark: Explode Cells
Counter_5
    DOMAIN = counter
    CNT_ATTR = _count
    START = 0
    SCOPE = Local
    -> AttributeExploder_2
AttributeExploder_2
    KEEP_GEOMETRY = No
    EXPLODING_TYPE = Features
    ATTR_VALUE_LABEL = _attr_value
    ATTR_NAME_LABEL = _attr_name
    KEEP_ATTRIBUTES = Yes
    -> ListSearcher_2

Bookmark: Add Rows
ListSearcher_2
    SEARCH_TYPE = First exact match
    INDEX_ATTR = _list_index
    ATTR_VALUE = @Value(_attr_name)
    LIST_ATTR = _list{}
    FOUND -> Sorter_2
Sorter_2
    SORT_PARM = _count NUMERIC ASCENDING _list_index NUMERIC ASCENDING
    SORTED -> Counter_3
Counter_3
    DOMAIN = counter
    CNT_ATTR = _count
    START = 0
    SCOPE = Local
    -> TextBoxAdder_3
    -> Tester
TextBoxAdder_3
    MINXVALATTR = $(MINXVALATTR)+@double(@Value(_count)%@Value(AttributeCount))*($(MAXXVALATTR)-$(MINXVALATTR))/@Value(AttributeCount)
    MINYVALATTR = $(MAXYVALATTR)-$(HEIGHT)*2-2*$(HEIGHT_2)*(@Value(_count)/(@Value(AttributeCount))+2)
    MAXXVALATTR = $(MINXVALATTR)+@double(@Value(_count)%@Value(AttributeCount)+1)*($(MAXXVALATTR)-$(MINXVALATTR))/(@Value(AttributeCount))
    HEIGHT = $(HEIGHT_2)
    MAXYVALATTR = $(MAXYVALATTR)-$(HEIGHT)*2-2*$(HEIGHT_2)*(@Value(_count)/@Value(AttributeCount)+1)
    LabelText = @Value(_attr_value)
    Box -> AttributeRemover_2
    Text -> AttributeRemover

Bookmark: Add Header
Tester
    TEST_DESCRIPTION = ""
    TEST_CLAUSE = TEST @Value(_count) < @Value(AttributeCount)
    BOOL_OP = OR
    TEST_MODE = Automatic
    PASSED -> TextBoxAdder
TextBoxAdder
    MINXVALATTR = $(MINXVALATTR)+@double(@Value(_count))*($(MAXXVALATTR)-$(MINXVALATTR))/@Value(AttributeCount)
    MINYVALATTR = $(MAXYVALATTR)-$(HEIGHT)*2-2*$(HEIGHT_2)
    MAXXVALATTR = $(MINXVALATTR)+@double(@Value(_count)+1)*($(MAXXVALATTR)-$(MINXVALATTR))/@Value(AttributeCount)
    HEIGHT = $(HEIGHT_2)
    MAXYVALATTR = $(MAXYVALATTR)-$(HEIGHT)*2
    LabelText = @Value(_attr_name)
    Box -> AttributeRemover_2
    Text -> AttributeRemover

Bookmark: Remove Attributes
AttributeRemover_2
    LIST_ATTRS = _list{}
    REMOVE_ATTRS = _ATTRLIST,AttributeCount,_count,_attr_name,_attr_value,_list_index
    -> Outline (output)
AttributeRemover
    LIST_ATTRS = _list{}
    REMOVE_ATTRS = _ATTRLIST,AttributeCount,_count,_attr_name,_attr_value,_list_index
    -> Text (output)

FME custom transformer PythonEmailer
This transformer sends emails that can contain attachments.
When a feature enters the PythonEmailer, it sends the file(s) set for its attachments parameter to the recipient(s). You can also include a custom message with the email.
This transformer uses code found at "http://dzone.com/snippets/send-email-attachments-python"
If you want this transformer to send the outputs of a writer in a workspace, encapsulate that workspace in a WorkspaceRunner transformer and make sure "Wait for Job To Complete" is set to "Yes", then connect the SUCCESS port of the WorkspaceRunner to PythonEmailer's Trigger port.
Attachments have to be entered as a list of comma separate values. For example: C:/file1.zip,C:/temp/file2.jpg
Recipients also have to be entered as a list of comma separated values.
If your email server does not need authentication, leave the Sender Username and Password parameters blank.
Attachments will have CID set to the base filename of the attached file, so you can embed them in an html message.
For example, if you attach c:\temp\file.jpg, you can embed it with
<img src="cid:file.jpg" />
in the HTML source for the message.
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_subject =   # Subject
- email_from =   # From
- attachments =   # Attachments
- email_to =   # Recipients
- email_server =   # Email Server
- server_port = 25   # Email Server Port
- cType = TLS   # Connection Type
- email_message =   # Email Message
- email_message_type = plain   # Email Message Type (Plain Text/HTML)
- username =   # Sender's Username
- password =   # Sender's Password

TRIGGER (input)
    -> ParameterFetcher
Note: Add parameters as attributes
ParameterFetcher
    ATTR_LIST = _email_subject {$(email_subject)} _email_from {$(email_from)} _Attachments {$(attachments)} _email_to {$(email_to)} _email_server {$(email_server)} _server_port {$(server_port)} _cType {$(cType)} _email_message {$(email_message)} _username {$(username)} _password {$(password)} _email_message_type {$(email_message_type)}
    -> PythonCaller
Note: Send mail.
PythonCaller
    PYTHONSYMBOL = email
    PYTHONSOURCE:
      # Original code found at "http://dzone.com/snippets/send-email-attachments-python" and modified by Arash Ouji.

      import smtplib, os, re
      from email.MIMEMultipart import MIMEMultipart
      from email.MIMEBase import MIMEBase
      from email.MIMEText import MIMEText
      from email.Utils import formatdate,COMMASPACE
      from email import Encoders

      # Main function
      def send_mail(send_from, send_to, subject, text, text_format, server, port, connection_type, username, password,attachments):

          # Create lists out of attachments and receipients strings
          filelist= re.split(",",attachments)
          tolist=re.split(",",send_to)

          # Create a container for the message and populate email headers
          msg = MIMEMultipart()
          msg['From'] = send_from
          msg['To'] = COMMASPACE.join(tolist)
          msg['Date'] = formatdate(localtime=True)
          msg['Subject'] = subject

          # Add email body text, forcing encoding to utf-8
          msg.attach( MIMEText(text,text_format,'utf-8') )

          # If there are any attachments, add them
          if (attachments!=''):
              for f in filelist:
                  part = MIMEBase('application', "octet-stream")
                  part.set_payload( open(f,"rb").read() )
                  Encoders.encode_base64(part)
                  part.add_header('Content-Disposition', 'attachment; filename="%s"' % os.path.basename(f))
                  part.add_header('Content-ID', '<%s>' % os.path.basename(f))
                  msg.attach(part)

          port = int (port)

          # Determine how we want to begin the connection
          if (connection_type=='TLS'):
              smtp=smtplib.SMTP(server,port)
          else:
              smtp = smtplib.SMTP_SSL(server,port)

          # If a username is provided, try to authenticate
          if (username!=''):
              smtp.login(username,password)

          # Send the email
          smtp.sendmail(send_from, tolist, msg.as_string())
          smtp.close()

      # Feature starting point
      def email(feature):

          # Retrieve all variables
          email_from=feature.getAttribute('_email_from')
          email_to=feature.getAttribute('_email_to')
          email_subject=feature.getAttribute('_email_subject')
          email_message=feature.getAttribute('_email_message')
          email_message_type=feature.getAttribute('_email_message_type')
          email_server=feature.getAttribute('_email_server')
          server_port=feature.getAttribute('_server_port')
          cType=feature.getAttribute('_cType')
          username=feature.getAttribute('_username')
          password=feature.getAttribute('_password')
          Attachments=feature.getAttribute('_Attachments')

          # Call the main function
          send_mail(email_from,email_to,email_subject,email_message,email_message_type,email_server,server_port,cType,username,password,Attachments)
