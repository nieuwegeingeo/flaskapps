FME workspace verblijfsobjecten_binnen_wijk_export.fmw

Parameters:
- EMAIL = m.kselik@nieuwegein.nl   # Email
- WIJKEN_SELECT = Batau Noord   # Selecteer wijken
- COORDS =   # Coordinaten
- GEBRUIK = alle gebruiksfuncties   # Gebruiksfunctie
- OUTPUT_TYPE = pdf   # PDF of Excel

Readers:
- ORACLE_SPATIAL_1: ORACLE_SPATIAL from vngp

Note: Selecteer wijk
Tester
    TEST_CLAUSE = TEST @Value(WIJKNAAM) IN $(WIJKEN_SELECT)
    TEST_DESCRIPTION = ""
    TEST_MODE = Automatic
    BOOL_OP = AND
    PASSED -> SpatialFilter [Filter]
Note: Als geen coordinaat, dan wijken.
GeometryFilter
    GEOM_PORT_NAMES = Point
    BREAK_AGG = No
    POINT -> PointOnAreaOverlayer [POINT]
PointOnAreaOverlayer
    ATTR_ACCUM_MODE = Merge Incoming
    POLYS_FIRST = NO
    ATTR_CONFLICT_RES = Use Original
    POINT -> SpatialFilter [Candidate]
SpatialFilter
    AGGREGATE_HANDLING = Yes
    PREDATTR = _predicate
    BASE_TYPE = Multiple Filters
    CURVE_BOUNDARY_RULE_PARAM = Default Rule
    USE_BOUNDING_BOX = No
    PREDICATES = INTERSECTS
    PASS_CRITERIA = Pass Against One Filter
    PASSED -> AttributeManager
AttributeManager
    ATTR_TABLE:
      RENAME_SET_VALUE OPENBARE_RUIMTE > STRAAT
      RENAME_SET_VALUE GEBRUIK > TYPE_GEBRUIK
      REMOVE WIJKKODE
      REMOVE ADRESSEN
      REMOVE ID
      REMOVE _predicate
      REMOVE _creation_instance
      REMOVE IDENTIFICATIECODE
      REMOVE INGANGSDATUM
      REMOVE STATUS
      REMOVE STATUS_AUTHENTICITEIT
      REMOVE DOCUMENT
      REMOVE DOCUMENTDATUM
      REMOVE INDICATIEGECONSTATEERD
      REMOVE IN_ONDERZOEK_GEMEENTE
    -> TestFilter
TestFilter
    TEST_LIST = BOOL_OP,OR,COMPOSITE_TEST,<Unused>,TEST_CLAUSE,"TEST $(OUTPUT_TYPE) = pdf",__OUTPUT_TYPE_ = pdf,BOOL_OP,OR,COMPOSITE_TEST,<Unused>,TEST_CLAUSE,"TEST $(OUTPUT_TYPE) = excel",__OUTPUT_TYPE_ = excel
    DEFAULT_VALUE = <UNFILTERED>
    __OUTPUT_TYPE_ = pdf -> Tester_7_PASSED_-__AttributeCreator
    __OUTPUT_TYPE_ = excel -> FeatureWriter [Output]
Tester_7_PASSED_-__AttributeCreator: Junction
    -> AttributeCreator
    -> Aggregator

Bookmark: Oracle input
Creator_3
    NUM = 1
    GEOMTYPE = Geometry Object
    CREATED -> SystemCaller_2
SystemCaller_2
    CMD = del /q c:\programs\flask\verblijfsobjecten\producten\*
    -> Tester_3
    -> Gebruik_creation_splitter [Tester_5_Input]
    -> Tester_2
FeatureReader
    FORMAT = ORACLE_SPATIAL
    ORACLE_SPATIAL_PASSWORD =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
    ATTRIBUTES = NIEUWEGEIN.GM_SP_WIJKEN,"WIJKKODE,WIJKNAAM,ADRESSEN,ID"
    ORACLE_SPATIAL_SHOW_SYSTEM_TABLES = NO
    INTERACT = <No Spatial Filter>
    ORACLE_SPATIAL_REMOVE_SCHEMA_QUALIFIER = NO
    ORACLE_SPATIAL_HANDLE_MULTIPLE_SPATIAL_COLUMNS = NO
    ORACLE_SPATIAL_PARSE_MAPINFO_SYMBOLOGY = NO
    ORACLE_SPATIAL_PERSISTENT_CONNECTION = YES
    ORACLE_SPATIAL_INTERACTION = ANYINTERACT
    FEATURETYPES = NIEUWEGEIN.GM_SP_WIJKEN
    ORACLE_SPATIAL_CLIP_TO_ENVELOPE = NO
    DATASET = vngp
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_WIJKEN -> Tester
Note: Dit is een Oracle VNGP input uitgesplitst / naar gebruiksfunctie t.b.v. filteren in het / web form.
Gebruik_creation_splitter
    GEBRUIK = $(GEBRUIK)
    -> GeometryFilter
NIEUWEGEIN.GM_SP_WIJKEN (reader ORACLE_SPATIAL_1)
    attributes: WIJKKODE number(5,0), WIJKNAAM varchar2(50), ADRESSEN varchar2(50), ID number(5,0)
    -> PointOnAreaOverlayer [AREA]

Bookmark: Test op coordinaten
Note: Tester_2 [Tester] / Test Description: "" / TEST $(COORDS) ATTRIBUTE_HAS_VALUE "" / Condition: OR
Tester_2
    TEST_CLAUSE = TEST $(COORDS) ATTRIBUTE_HAS_VALUE ""
    TEST_DESCRIPTION = ""
    TEST_MODE = Automatic
    BOOL_OP = OR
    PASSED -> GeometryReplacer_2
    FAILED -> FeatureReader [INITIATOR]
Note: Toekennen wktstring parameter / $COORDS
GeometryReplacer_2
    OGC_WKT_PRECISION_DISPLAY = 32-bit
    KIND_LONG = OGC Well Known Text
    REMOVE_ATTRIBUTE = No
    SOURCE = $(COORDS)
    -> GeometryFilter_2
    <REJECTED> -> Terminator_2
GeometryFilter_2
    GEOM_PORT_NAMES = Area
    BREAK_AGG = No
    AREA -> GeometryValidator
GeometryValidator
    CHECK_HOLE_TOUCHING_POLYGON = No
    ISSUE_ATTR_NAME = _issues
    REPAIR = Yes
    SELF_INTERSECTING = SELF_INTERSECTING
    PRESETS = Custom
    OGC_VALID_CHECK = OGC_VALID_CHECK
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PASSED -> SpatialFilter [Filter]
    FAILED -> Terminator_3
Terminator_3
    MESSAGE = Foutive geometrie
Terminator_2
    MESSAGE = Foutive geometrie

Bookmark: Mail adres tester
Note: Alleen @nieuwegein.nl adressen worden doorgelaten
Tester_3
    TEST_CLAUSE = TEST $(EMAIL) LIKE %@nieuwegein.nl
    TEST_DESCRIPTION = ""
    TEST_MODE = Automatic
    BOOL_OP = OR
    PASSED -> GeometryFilter
    FAILED -> Terminator
Terminator
    MESSAGE = Translation Terminated

Bookmark: kaart extract
Aggregator
    ACCUM_ATTRS_NAME = Get Attributes From One Representative Feature
    ORDERED = No
    MODE = Geometry - Assemble One Level
    SEP = ,
    AGGREGATE_TYPE = Homogeneous Collection (If Possible)
    AGGREGATE -> BoundingBoxReplacer
    AGGREGATE -> FeatureWriter_3 [Aggregate]
BoundingBoxReplacer
    BOXTYPE = Bounding Box
    BOX -> Bufferer
Bufferer
    CAP_STYLE = Round
    OFFSET = 100
    INTERP_SEGMENTS = 8
    BUFFERED -> BoundsExtractor
BoundsExtractor
    XMAX = _xmax
    XMIN = _xmin
    ZMIN = _zmin
    YMIN = _ymin
    ZMAX = _zmax
    YMAX = _ymax
    -> FeatureHolder
FeatureWriter_3
    ESRISHAPE_UPPER_CASE_ATTR_NAMES = No
    WRITER_DIRECTIVES = SHAPE_WRT_ADV_PARM_GROUP,FME_DISCLOSURE_OPEN,PRESERVE_RING_VERTEX_ORDER,No,WRITE_SPATIAL_INDEX,No,SURFACE_AND_SOLID_STORAGE,shape_multipatch,UPPER_CASE_ATTR_NAMES,No,DIMENSION,auto,DESTINATION_DATASETTYPE_VALIDATION,Yes,ENCODING,SYSTEM,DIMENSION_GROUP,FME_DISCLOSURE_CLOSED,COMPRESSED_SHAPE_FILE,No,STRICT_COMPATIBILITY,Yes
    DATASET = $(FME_MF_DIR_ENCODED)producten
    ESRISHAPE_WRITE_SPATIAL_INDEX = No
    ESRISHAPE_PRESERVE_RING_VERTEX_ORDER = No
    TOTAL_FEATURES_WRITTEN_ATTR = _total_features_written
    COORDSYS = EPSG:28992
    FEATURE_TYPE_LIST_ATTR = _feature_type
    ESRISHAPE_STRICT_COMPATIBILITY = Yes
    DATASET_ATTR = _dataset
    ESRISHAPE_DIMENSION = auto
    ESRISHAPE_COMPRESSED_SHAPE_FILE = No
    ESRISHAPE_ENCODING = SYSTEM
    FORMAT = ESRISHAPE
    ESRISHAPE_DESTINATION_DATASETTYPE_VALIDATION = Yes
    ESRISHAPE_SURFACE_AND_SOLID_STORAGE = shape_multipatch
    SUMMARY -> FeatureHolder
FeatureHolder
    -> GeometryFilter_3
GeometryFilter_3
    GEOM_PORT_NAMES = Area
    BREAK_AGG = No
    AREA -> WorkspaceRunner
WorkspaceRunner
    WORKSPACE_FILE = $(FME_MF_DIR)overzicht_voor_rapport.fmw
    WORKSPACE_PARAMETERS = SourceDataset_ESRISHAPE,$(FME_MF_DIR_USERTYPED)producten\vbo_points.shp,DestDataset_JPEG,$(FME_MF_DIR_USERTYPED)producten,SourceDataset_WMS,http://gng-ap713.nieuwegein.nl/mapproxy/service?REQUEST=GetCapabilities,WMS_IN_SEARCH_ENVELOPE_MINX_WMS,@Value(_xmin),WMS_IN_SEARCH_ENVELOPE_MINY_WMS,@Value(_ymin),WMS_IN_SEARCH_ENVELOPE_MAXX_WMS,@Value(_xmax),WMS_IN_SEARCH_ENVELOPE_MAXY_WMS,@Value(_ymax)
    BLOCKING = Yes
    SUCCEEDED -> FeatureReader_2 [INITIATOR]

Bookmark: Rapport creator
FeatureReader_2
    FORMAT = JPEG
    ATTRIBUTES = JPEG,
    JPEG_APPLY_GCPS = No
    JPEG_GROUP_BY_DATASET = No
    INTERACT = <No Spatial Filter>
    JPEG_USE_SEARCH_ENVELOPE = NO
    DATASET = $(FME_MF_DIR_ENCODED)producten\rapport_foto.jpg
    COMBINE_GEOM = Use Result
    JPEG_CLIP_TO_ENVELOPE = NO
    OUTPUT_FEATURES_DISPLAY = Schema and Data Features
    ATTR_ACCUM_MODE = Only Use Result
    JPEG -> Tester_7
Tester_7
    TEST_CLAUSE = TEST $(WIJKEN_SELECT) = alle_wijken
    TEST_DESCRIPTION = ""
    TEST_MODE = Automatic
    BOOL_OP = OR
    PASSED -> PDFPageFormatter_2 [JPEG]
    FAILED -> PDFPageFormatter [JPEG]
AttributeCreator
    ATTR_TABLE = SET_TO AANTAL = 1
    -> AttributePivoter
AttributePivoter
    GROUP_TOTALS_TAG = Total
    ROW_GROUP_ATTRS = TYPE_GEBRUIK
    PIVOT_SUMMARY_TYPES = Count
    PIVOT_ATTR = AANTAL
    DATA -> AttributeManager_2
AttributeManager_2
    ATTR_TABLE:
      RENAME_SET_VALUE TYPE_GEBRUIK > Gebruik
      RENAME_SET_VALUE AANTAL > Aantal
      REMOVE WIJKNAAM
      REMOVE STRAAT
      REMOVE HUISNUMMER
      REMOVE HUISLETTER
      REMOVE HUISNUMMERTOEVOEGING
      REMOVE POSTCODE
      REMOVE WOONPLAATS
      REMOVE OPPERVLAKTE
    -> TableAdder
TableAdder
    ChartTitle = Aantal verblijfsobjecten per type
    MAXXVALATTR = 0
    MAXYVALATTR = 0
    HEIGHT = 14
    MINXVALATTR = 1000
    HEIGHT_2 = 10
    ATTRLIST = Aantal Gebruik
    Outline -> PDFStyler_2
    Text -> TestFilter_2
PDFStyler_2
    OPACITY = 1.0
    COLOR = 0,0,0
    LINE_DASH_PHASE = 0
    LINE_MITER_LIMIT = 0.0
    FILL_COLOR = 1,1,1
    FONT = MS Sans Serif,12
    LINE_CAP_STYLE_PARAM = Butt Cap
    FILL_OPACITY = 0.00
    LINE_WIDTH = 1.0
    LINE_JOIN_STYLE_PARAM = Miter Join
    PDFStyled -> AttributeCreator_2
AttributeCreator_2
    ATTR_TABLE = SET_TO SORT = 1
    -> Sorter
FeatureColorSetter
    MODE = Fixed
    COLOR = 0,0,0
    FILL_COLOR = 0,0,0
    COLORED -> Tester_9
Tester_9
    TEST_CLAUSE = TEST @Value(Font) = Arial,10
    TEST_DESCRIPTION = ""
    TEST_MODE = Automatic
    BOOL_OP = OR
    PASSED -> PDFStyler_3
    FAILED -> AttributeCreator_3
PDFStyler_3
    OPACITY = 1.0
    COLOR = 0,0,0
    LINE_DASH_PHASE = 0
    LINE_MITER_LIMIT = 0.0
    FILL_COLOR = 0,0,0
    FONT = MS Sans Serif,8
    LINE_CAP_STYLE_PARAM = Butt Cap
    FILL_OPACITY = 1.00
    LINE_WIDTH = 1.0
    LINE_JOIN_STYLE_PARAM = Miter Join
    PDFStyled -> AttributeCreator_3
AttributeCreator_3
    ATTR_TABLE = SET_TO SORT = 2
    -> Sorter
Sorter
    SORT_PARM = Label ALPHA ASCENDING
    SORTED -> Tester_8
Tester_8
    TEST_CLAUSE = TEST $(WIJKEN_SELECT) = alle_wijken
    TEST_DESCRIPTION = ""
    TEST_MODE = Automatic
    BOOL_OP = OR
    PASSED -> PDFPageFormatter_2 [HTML TABLE]
    FAILED -> PDFPageFormatter [HTML TABLE]
PDFPageFormatter_2
    PAGE_HEIGHT_USER = 11.69
    PAGE_ORIENTATION = Portrait
    PAGE_NUMBER = 1
    PAGE_HEIGHT_PTS = 842
    PAGE_OBJECTS = "HTML TABLE CLIPPING_ENABLED;No;MINX;72;SIZE_PARAMS;;WIDTH;451.44;HEIGHT;548.87;MINY;0.320007;FIXED_ASPECT;Yes;SCALING_PARAMS;","JPEG CLIPPING_ENABLED;No;MINX;7.2;SIZE_PARAMS;;WIDTH;581.04;HEIGHT;275.74;MINY;559.063;FIXED_ASPECT;Yes;SCALING_PARAMS;"
    PAGE_WIDTH_USER = 8.27
    PAGE_UNITS = Inches
    PAGE_WIDTH_PTS = 595
    PAGE_SIZE = A4
PDFPageFormatter
    PAGE_HEIGHT_USER = 11.69
    PAGE_ORIENTATION = Portrait
    PAGE_NUMBER = 1
    PAGE_HEIGHT_PTS = 842
    PAGE_OBJECTS = "HTML TABLE MINY;0.320007;HEIGHT;467.28;FIXED_ASPECT;Yes;CLIPPING_ENABLED;No;MINX;7.2;SCALING_PARAMS;;SIZE_PARAMS;;WIDTH;581.04","JPEG MINY;474.8;HEIGHT;360;FIXED_ASPECT;Yes;CLIPPING_ENABLED;No;MINX;7.2;SCALING_PARAMS;;SIZE_PARAMS;;WIDTH;581.04"
    PAGE_WIDTH_USER = 8.27
    PAGE_UNITS = Inches
    PAGE_WIDTH_PTS = 595
    PAGE_SIZE = A4
    -> FeatureWriter_2 [Output]
FeatureWriter_2
    PDF2D_SCALE_TEXT_FONT = No
    PDF2D_COMPRESS_STREAMS = Yes
    WRITER_DIRECTIVES = SCALE_TEXT_FONT,No,DEFAULT_OPACITY,0.4,COMPRESS_STREAMS,Yes,DEFAULT_LINE_WIDTH,1.0,DEFAULT_POINT_SIZE,1.0,PANEL_VISIBILITY,Layers,RICH_TEXT,No,WRITE_ATTRIBUTES,Yes,RANDOMIZE_FEATURE_TYPE_COLOR,Yes,DESTINATION_DATASETTYPE_VALIDATION,Yes,PDF14_COMPATIBLE,No,PAGE_SIZE,Letter
    DATASET = $(FME_MF_DIR_ENCODED)producten\Verblijfsobjecten_rapport.pdf
    PDF2D_PANEL_VISIBILITY = Layers
    PDF2D_DESTINATION_DATASETTYPE_VALIDATION = Yes
    PDF2D_DEFAULT_POINT_SIZE = 1.0
    TOTAL_FEATURES_WRITTEN_ATTR = _total_features_written
    FEATURE_TYPE_LIST_ATTR = _feature_type
    PDF2D_DEFAULT_LINE_WIDTH = 1.0
    PDF2D_RANDOMIZE_FEATURE_TYPE_COLOR = Yes
    PDF2D_DEFAULT_OPACITY = 0.4
    PDF2D_WRITE_ATTRIBUTES = Yes
    DATASET_ATTR = _dataset
    PDF2D_RICH_TEXT = No
    PDF2D_PDF14_COMPATIBLE = No
    FORMAT = PDF2D
    PDF2D_PAGE_SIZE = Letter
    SUMMARY -> Tester_4

Bookmark: Text uitlijnen naar links
TestFilter_2
    TEST_LIST:
      BOOL_OP,OR,COMPOSITE_TEST,<Unused>,TEST_CLAUSE,"TEST @Value(Label) = Gebruik
      TEST @Value(Label) = Aantal",@Value(Label) = gebruik,BOOL_OP,OR,COMPOSITE_TEST,<Unused>,TEST_CLAUSE,"TEST @Value(Font) = Arial,14
      TEST @Value(Label) CONTAINS_REGEX [0-9]",@Value(Font) = Arial,14
    DEFAULT_VALUE = <UNFILTERED>
    @Value(Label) = gebruik -> FeatureColorSetter
    @Value(Font) = Arial,14 -> FeatureColorSetter
    <UNFILTERED> -> CoordinateExtractor
CoordinateExtractor
    MODE = Specify Coordinate
    Z_ATTR = _z
    IND = 0
    X_ATTR = _x
    Y_ATTR = _y
    -> CoordinateReplacer
CoordinateReplacer
    FIND_X = @Value(_x)
    REPLACE_X = 10
    -> FeatureColorSetter

Bookmark: Excel writer
FeatureWriter
    XLSXW_RASTER_FORMAT = PNG
    WRITER_DIRECTIVES = TEMPLATE_SHEET,Verblijfsobjecten,OVERWRITE_FILE,No,FIELD_NAMES_OUT,Yes,DROP_TABLE,Yes,RASTER_FORMAT,PNG,TRUNCATE_TABLE,No,WRITER_MODE,Insert,DESTINATION_DATASETTYPE_VALIDATION,Yes,TEMPLATEFILE,$(FME_MF_DIR$encode)templates\verblijfsobjecten_template.xlsx
    DATASET = $(FME_MF_DIR_ENCODED)producten\verblijfsobjecten_download.xlsx
    XLSXW_WRITER_MODE = Insert
    XLSXW_TRUNCATE_TABLE = No
    XLSXW_DROP_TABLE = Yes
    XLSXW_FIELD_NAMES_OUT = Yes
    XLSXW_TEMPLATE_SHEET = Verblijfsobjecten
    TOTAL_FEATURES_WRITTEN_ATTR = _total_features_written
    XLSXW_OVERWRITE_FILE = No
    FEATURE_TYPE_LIST_ATTR = _feature_type
    XLSXW_DESTINATION_DATASETTYPE_VALIDATION = Yes
    DATASET_ATTR = _dataset
    XLSXW_TEMPLATEFILE = $(FME_MF_DIR)templates\verblijfsobjecten_template.xlsx
    FORMAT = XLSXW
    SUMMARY -> Tester_4

Bookmark: Mailer
Tester_4
    TEST_CLAUSE = TEST $(COORDS) ATTRIBUTE_HAS_VALUE ""
    TEST_DESCRIPTION = ""
    TEST_MODE = Automatic
    BOOL_OP = OR
    PASSED -> StringConcatenator
    FAILED -> StringConcatenator_2
StringConcatenator
    VAL_ATTR = _result
    PARM_LINE:
      Hallo,

      Hierbij ontvangt u de verblijfsobjecten binnen het geselecteerde gebied . Mocht u nog vragen hebben kunt u ons mailen op geo-informatie@nieuwegein.nl

      Met vriendelijke groet,

      Team Geo-Informatie
    ACTION = Create New Attribute
    -> PythonEmailer [TRIGGER]
StringConcatenator_2
    VAL_ATTR = _result
    PARM_LINE:
      Hallo,

      Hierbij ontvangt u de verblijfsobjecten binnen de wijk(en) $(WIJKEN_SELECT). Mocht u nog vragen hebben kunt u ons mailen op geo-informatie@nieuwegein.nl

      Met vriendelijke groet,

      Team Geo-Informatie
    ACTION = Create New Attribute
    -> PythonEmailer [TRIGGER]
PythonEmailer
    email_message_type = plain
    email_to = $(EMAIL)
    email_server = "smtp.nieuwegein.nl "
    server_port = 25
    attachments = @Value(_dataset)
    cType = TLS
    email_from = geo-informatie@nieuwegein.nl
    email_subject = Opgevraagde verblijfsobjecten
    email_message = @Value(_result)

FME custom transformer Gebruik_creation_splitter

Parameters:
- GEBRUIK =   # Gebruiksfunctie

Tester_5_Input (input)
    -> Tester_5
    -> Tester_2
    -> Tester_3
    -> Tester_4
    -> Tester_6
    -> Tester_7
    -> Tester_8
    -> Tester_9
    -> Tester_10
    -> Tester_11
    -> Tester_12
    -> Tester_13
Note: Bijeenkomstfunctie
Tester_5
    TEST_CLAUSE = TEST $(GEBRUIK) CONTAINS bijeenkomstfunctie
    TEST_DESCRIPTION = ""
    TEST_MODE = Automatic
    BOOL_OP = OR
    PASSED -> FeatureReader [INITIATOR]
FeatureReader
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    WHERE = GEBRUIK LIKE '%bijeenkomstfunctie%'
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
Note: Celfunctie
Tester_2
    TEST_CLAUSE = TEST $(GEBRUIK) CONTAINS celfunctie
    TEST_DESCRIPTION = ""
    TEST_MODE = Automatic
    BOOL_OP = OR
    PASSED -> FeatureReader_2 [INITIATOR]
FeatureReader_2
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    WHERE = GEBRUIK LIKE '%celfunctie%'
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
Note: gezondheidszorgfunctie
Tester_3
    TEST_CLAUSE = TEST $(GEBRUIK) CONTAINS gezondheidszorgfunctie
    TEST_DESCRIPTION = ""
    TEST_MODE = Automatic
    BOOL_OP = OR
    PASSED -> FeatureReader_3 [INITIATOR]
FeatureReader_3
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    WHERE = GEBRUIK LIKE '%gezondheidszorgfunctie%'
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
Note: industriefunctie
Tester_4
    TEST_CLAUSE = TEST $(GEBRUIK) CONTAINS industriefunctie
    TEST_DESCRIPTION = ""
    TEST_MODE = Automatic
    BOOL_OP = OR
    PASSED -> FeatureReader_7 [INITIATOR]
FeatureReader_7
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    WHERE = GEBRUIK LIKE '%industriefunctie%'
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
Note: kantoorfunctie
Tester_6
    TEST_CLAUSE = TEST $(GEBRUIK) CONTAINS kantoorfunctie
    TEST_DESCRIPTION = ""
    TEST_MODE = Automatic
    BOOL_OP = OR
    PASSED -> FeatureReader_4 [INITIATOR]
FeatureReader_4
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    WHERE = GEBRUIK LIKE '%kantoorfunctie%'
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
Note: logiesfunctie
Tester_7
    TEST_CLAUSE = TEST $(GEBRUIK) CONTAINS logiesfunctie
    TEST_DESCRIPTION = ""
    TEST_MODE = Automatic
    BOOL_OP = OR
    PASSED -> FeatureReader_5 [INITIATOR]
FeatureReader_5
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    WHERE = GEBRUIK LIKE '%logiesfunctie%'
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
Note: onderwijsfunctie
Tester_8
    TEST_CLAUSE = TEST $(GEBRUIK) CONTAINS onderwijsfunctie
    TEST_DESCRIPTION = ""
    TEST_MODE = Automatic
    BOOL_OP = OR
    PASSED -> FeatureReader_6 [INITIATOR]
FeatureReader_6
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    WHERE = GEBRUIK LIKE '%onderwijsfunctie%'
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
Note: overige gebruiksfunctie
Tester_9
    TEST_CLAUSE = TEST $(GEBRUIK) CONTAINS overige gebruiksfunctie
    TEST_DESCRIPTION = ""
    TEST_MODE = Automatic
    BOOL_OP = OR
    PASSED -> FeatureReader_8 [INITIATOR]
FeatureReader_8
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    WHERE = GEBRUIK LIKE '%overige gebruiksfunctie%'
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
Note: sportfunctie
Tester_10
    TEST_CLAUSE = TEST $(GEBRUIK) CONTAINS sportfunctie
    TEST_DESCRIPTION = ""
    TEST_MODE = Automatic
    BOOL_OP = OR
    PASSED -> FeatureReader_9 [INITIATOR]
FeatureReader_9
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    WHERE = GEBRUIK LIKE '%sportfunctie%'
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
Note: winkelfunctie
Tester_11
    TEST_CLAUSE = TEST $(GEBRUIK) CONTAINS winkelfunctie
    TEST_DESCRIPTION = ""
    TEST_MODE = Automatic
    BOOL_OP = OR
    PASSED -> FeatureReader_13 [INITIATOR]
FeatureReader_13
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    WHERE = GEBRUIK LIKE '%winkelfunctie%'
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
Note: woonfunctie
Tester_12
    TEST_CLAUSE = TEST $(GEBRUIK) CONTAINS woonfunctie
    TEST_DESCRIPTION = ""
    TEST_MODE = Automatic
    BOOL_OP = OR
    PASSED -> FeatureReader_10 [INITIATOR]
FeatureReader_10
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    WHERE = GEBRUIK LIKE '%woonfunctie%'
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
Note: Alles
Tester_13
    TEST_CLAUSE = TEST $(GEBRUIK) CONTAINS alle gebruiksfuncties
    TEST_DESCRIPTION = ""
    TEST_MODE = Automatic
    BOOL_OP = OR
    PASSED -> FeatureReader_11 [INITIATOR]
FeatureReader_11
    FORMAT = ORACLE_SPATIAL
    ORACLE_SPATIAL_PASSWORD =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
    ATTRIBUTES = NIEUWEGEIN.GM_SP_BAG_VERBLIJFSOBJECTEN,"IDENTIFICATIECODE,INGANGSDATUM,OPENBARE_RUIMTE,HUISNUMMER,HUISLETTER,HUISNUMMERTOEVOEGING,POSTCODE,WOONPLAATS,STATUS,STATUS_AUTHENTICITEIT,DOCUMENT,DOCUMENTDATUM,INDICATIEGECONSTATEERD,IN_ONDERZOEK_GEMEENTE,OPPERVLAKTE,GEBRUIK"
    ORACLE_SPATIAL_SHOW_SYSTEM_TABLES = NO
    INTERACT = <No Spatial Filter>
    ORACLE_SPATIAL_REMOVE_SCHEMA_QUALIFIER = NO
    ORACLE_SPATIAL_PARSE_MAPINFO_SYMBOLOGY = NO
    ORACLE_SPATIAL_HANDLE_MULTIPLE_SPATIAL_COLUMNS = NO
    ORACLE_SPATIAL_PERSISTENT_CONNECTION = YES
    ORACLE_SPATIAL_INTERACTION = ANYINTERACT
    FEATURETYPES = NIEUWEGEIN.GM_SP_BAG_VERBLIJFSOBJECTEN
    ORACLE_SPATIAL_CLIP_TO_ENVELOPE = NO
    DATASET = vngp
    ORACLE_SPATIAL_QUERY_FEATURE_TYPES_FOR_MERGE_FILTERS = Yes
    COMBINE_GEOM = Use Result
    ORACLE_SPATIAL_CHUNK_SIZE = 200
    ORACLE_SPATIAL_SERVER_TYPE = ORACLE8i
    ORACLE_SPATIAL_USER_NAME = NIEUWEGEIN
    OUTPUT_FEATURES_DISPLAY = Schema and Data Features
    ATTR_ACCUM_MODE = Only Use Result
    ORACLE_SPATIAL_USE_SEARCH_ENVELOPE = NO
    ORACLE_SPATIAL_INTERRESULT = = 'TRUE'
    ORACLE_SPATIAL_USE_UNIFIED_DATE_ATTRS = YES
    ORACLE_SPATIAL_READ_3D_POLYGON_AS_FACE = NO
    NIEUWEGEIN.GM_SP_BAG_VERBLIJFSOBJECTEN -> FeatureReader_13_NIEUWEGEIN.GM_SP_BAG_VERBLIJFSOBJECTEN_-__DuplicateFilter
FeatureReader_13_NIEUWEGEIN.GM_SP_BAG_VERBLIJFSOBJECTEN_-__DuplicateFilter: Junction
    -> DuplicateFilter
DuplicateFilter
    KEYATTR = IDENTIFICATIECODE
    INPUT_ORDERED_CHOICE = No
    UNIQUE -> Output (output)
Output (output)

FME custom transformer TextBoxAdder

Parameters:
- MINXVALATTR =   # Min X Value
- MINYVALATTR =   # Min Y Value
- MAXXVALATTR =   # Max X Value
- MAXYVALATTR =   # Max Y Value
- HEIGHT = 18   # Label Height
- LabelText =   # Label Text

INPUT (input)
    -> 2DBoxReplacer
Box (output)
Text (output)

Bookmark: Create Box
2DBoxReplacer
    MAXXVALATTR = $(MAXXVALATTR)
    MAXYVALATTR = $(MAXYVALATTR)
    MINXVALATTR = $(MINXVALATTR)
    MINYVALATTR = $(MINYVALATTR)
    BOX -> CenterPointReplacer_2
    BOX -> Box (output)

Bookmark: Add Label
CenterPointReplacer_2
    CENTERPOINT -> CoordinateExtractor_2
CoordinateExtractor_2
    Z_DEFAULT = -9999
    Z_ATTR = _z
    IND = 0
    X_ATTR = _x
    Y_ATTR = _y
    -> AttributeCreator
AttributeCreator
    ATTR_LIST = Font,Arial,$(HEIGHT),Label,$(LabelText)
    -> LabelPointReplacer_2
LabelPointReplacer_2
    LABATTR = Label
    ALWAYSROTATE = no
    HEIGHT = $(HEIGHT)
    LABELPOINT -> BoundingBoxReplacer

Bookmark: Center Justify Label
BoundingBoxReplacer
    BOXTYPE = Bounding Box
    BOX -> CenterPointReplacer
CenterPointReplacer
    CENTERPOINT -> CoordinateExtractor
CoordinateExtractor
    Z_DEFAULT = -9999
    Z_ATTR = _zt
    IND = 0
    X_ATTR = _xt
    Y_ATTR = _yt
    -> 2DPointReplacer
2DPointReplacer
    YVALATTR = @Value(_y)-(@Value(_yt)-@Value(_y))
    XVALATTR = @Value(_x)-(@Value(_xt)-@Value(_x))
    POINT -> LabelPointReplacer
LabelPointReplacer
    LABATTR = Label
    ALWAYSROTATE = yes
    HEIGHT = $(HEIGHT)
    LABELPOINT -> Text (output)

FME custom transformer PythonEmailer
This transformer sends emails that can contain attachments.
When a feature enters the PythonEmailer, it sends the file(s) set for its attachments parameter to the recipient(s). You can also include a custom message with the email.
This transformer uses code found at "http://dzone.com/snippets/send-email-attachments-python"
If you want this transformer to send the outputs of a writer in a workspace, encapsulate that workspace in a WorkspaceRunner transformer and make sure "Wait for Job To Complete" is set to "Yes", then connect the SUCCESS port of the WorkspaceRunner to PythonEmailer's Trigger port.
Attachments have to be entered as a list of comma separate values. For example: C:/file1.zip,C:/temp/file2.jpg
Recipients also have to be entered as a list of comma separated values.
If your email server does not need authentication, leave the Sender Username and Password parameters blank.
Attachments will have CID set to the base filename of the attached file, so you can embed them in an html message.
For example, if you attach c:\temp\file.jpg, you can embed it with
<img src="cid:file.jpg" />
in the HTML source for the message.
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_subject =   # Subject
- email_from =   # From
- attachments =   # Attachments
- email_to =   # Recipients
- email_server =   # Email Server
- server_port = 25   # Email Server Port
- cType = TLS   # Connection Type
- email_message =   # Email Message
- email_message_type = plain   # Email Message Type (Plain Text/HTML)
- username =   # Sender's Username
- password =   # Sender's Password

TRIGGER (input)
    -> ParameterFetcher
Note: Add parameters as attributes
ParameterFetcher
    ATTR_LIST = _email_subject {$(email_subject)} _email_from {$(email_from)} _Attachments {$(attachments)} _email_to {$(email_to)} _email_server {$(email_server)} _server_port {$(server_port)} _cType {$(cType)} _email_message {$(email_message)} _username {$(username)} _password {$(password)} _email_message_type {$(email_message_type)}
    -> PythonCaller
Note: Send mail.
PythonCaller
    PYTHONSYMBOL = email
    PYTHONSOURCE:
      # Original code found at "http://dzone.com/snippets/send-email-attachments-python" and modified by Arash Ouji.

      import smtplib, os, re
      from email.MIMEMultipart import MIMEMultipart
      from email.MIMEBase import MIMEBase
      from email.MIMEText import MIMEText
      from email.Utils import formatdate,COMMASPACE
      from email import Encoders

      # Main function
      def send_mail(send_from, send_to, subject, text, text_format, server, port, connection_type, username, password,attachments):

          # Create lists out of attachments and receipients strings
          filelist= re.split(",",attachments)
          tolist=re.split(",",send_to)

          # Create a container for the message and populate email headers
          msg = MIMEMultipart()
          msg['From'] = send_from
          msg['To'] = COMMASPACE.join(tolist)
          msg['Date'] = formatdate(localtime=True)
          msg['Subject'] = subject

          # Add email body text, forcing encoding to utf-8
          msg.attach( MIMEText(text,text_format,'utf-8') )

          # If there are any attachments, add them
          if (attachments!=''):
              for f in filelist:
                  part = MIMEBase('application', "octet-stream")
                  part.set_payload( open(f,"rb").read() )
                  Encoders.encode_base64(part)
                  part.add_header('Content-Disposition', 'attachment; filename="%s"' % os.path.basename(f))
                  part.add_header('Content-ID', '<%s>' % os.path.basename(f))
                  msg.attach(part)

          port = int (port)

          # Determine how we want to begin the connection
          if (connection_type=='TLS'):
              smtp=smtplib.SMTP(server,port)
          else:
              smtp = smtplib.SMTP_SSL(server,port)

          # If a username is provided, try to authenticate
          if (username!=''):
              smtp.login(username,password)

          # Send the email
          smtp.sendmail(send_from, tolist, msg.as_string())
          smtp.close()

      # Feature starting point
      def email(feature):

          # Retrieve all variables
          email_from=feature.getAttribute('_email_from')
          email_to=feature.getAttribute('_email_to')
          email_subject=feature.getAttribute('_email_subject')
          email_message=feature.getAttribute('_email_message')
          email_message_type=feature.getAttribute('_email_message_type')
          email_server=feature.getAttribute('_email_server')
          server_port=feature.getAttribute('_server_port')
          cType=feature.getAttribute('_cType')
          username=feature.getAttribute('_username')
          password=feature.getAttribute('_password')
          Attachments=feature.getAttribute('_Attachments')

          # Call the main function
          send_mail(email_from,email_to,email_subject,email_message,email_message_type,email_server,server_port,cType,username,password,Attachments)

FME custom transformer TableAdder
Generates a vector-based table of attribute data for writing to pdf or other vector formats
Users specify the minimum and maximum coordinates of the table as well as the maximum y coordinate. Attributes to be summarized are selected. A table name can also be given. The length of the table will depend on the number of attributes and the font size specified. Table text and boundaries can be later styled with other styler transformers such as the PDF Styler.
Copyright (c) 2013 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- FME_PROCESS_GROUP_BY =   # " " Group By
- ChartTitle = Title   # Chart Title
- MINXVALATTR =   # Min X Value
- MAXXVALATTR =   # Max X Value
- MAXYVALATTR =   # Max Y Value
- HEIGHT = 18   # Title Height
- HEIGHT_2 = 12   # Row Text Height
- ATTRLIST =   # Selected Attributes

INPUT (input)
    -> TextBoxAdder_2
    -> ParameterFetcher
Outline (output)
Text (output)

Bookmark: Add Title
TextBoxAdder_2
    LabelText = $(ChartTitle)
    MAXXVALATTR = $(MAXXVALATTR)
    MAXYVALATTR = $(MAXYVALATTR)
    HEIGHT = $(HEIGHT)
    MINXVALATTR = $(MINXVALATTR)
    MINYVALATTR = $(MAXYVALATTR)-$(HEIGHT)*2
    Box -> AttributeRemover_2
    Text -> AttributeRemover

Bookmark: Calculate Number of Columns
ParameterFetcher
    ATTR_LIST = _ATTRLIST {$(ATTRLIST)}
    -> AttributeSplitter
AttributeSplitter
    ATTR_NAME = _ATTRLIST
    DROP_EMPTY_PARTS = No
    DELIMITER = " "
    LIST_NAME = _list
    TRIM_OPTION = Both
    -> ListElementCounter
ListElementCounter
    CNT_ATTR = AttributeCount
    LIST_NAME = _list{}
    -> Counter_5

Bookmark: Explode Cells
Counter_5
    CNT_ATTR = _count
    SCOPE = Local
    START = 0
    DOMAIN = counter
    -> AttributeExploder_2
AttributeExploder_2
    ATTR_VALUE_LABEL = _attr_value
    KEEP_ATTRIBUTES = Yes
    KEEP_GEOMETRY = No
    EXPLODING_TYPE = Features
    ATTR_NAME_LABEL = _attr_name
    -> ListSearcher_2

Bookmark: Add Rows
ListSearcher_2
    LIST_ATTR = _list{}
    INDEX_ATTR = _list_index
    SEARCH_TYPE = First exact match
    ATTR_VALUE = @Value(_attr_name)
    FOUND -> Sorter_2
Sorter_2
    SORT_PARM = _count NUMERIC ASCENDING _list_index NUMERIC ASCENDING
    SORTED -> Counter_3
Counter_3
    CNT_ATTR = _count
    SCOPE = Local
    START = 0
    DOMAIN = counter
    -> TextBoxAdder_3
    -> Tester
TextBoxAdder_3
    LabelText = @Value(_attr_value)
    MAXXVALATTR = $(MINXVALATTR)+@double(@Value(_count)%@Value(AttributeCount)+1)*($(MAXXVALATTR)-$(MINXVALATTR))/(@Value(AttributeCount))
    MAXYVALATTR = $(MAXYVALATTR)-$(HEIGHT)*2-2*$(HEIGHT_2)*(@Value(_count)/@Value(AttributeCount)+1)
    HEIGHT = $(HEIGHT_2)
    MINXVALATTR = $(MINXVALATTR)+@double(@Value(_count)%@Value(AttributeCount))*($(MAXXVALATTR)-$(MINXVALATTR))/@Value(AttributeCount)
    MINYVALATTR = $(MAXYVALATTR)-$(HEIGHT)*2-2*$(HEIGHT_2)*(@Value(_count)/(@Value(AttributeCount))+2)
    Box -> AttributeRemover_2
    Text -> AttributeRemover

Bookmark: Add Header
Tester
    TEST_CLAUSE = TEST @Value(_count) < @Value(AttributeCount)
    TEST_DESCRIPTION = ""
    TEST_MODE = Automatic
    BOOL_OP = OR
    PASSED -> TextBoxAdder
TextBoxAdder
    LabelText = @Value(_attr_name)
    MAXXVALATTR = $(MINXVALATTR)+@double(@Value(_count)+1)*($(MAXXVALATTR)-$(MINXVALATTR))/@Value(AttributeCount)
    MAXYVALATTR = $(MAXYVALATTR)-$(HEIGHT)*2
    HEIGHT = $(HEIGHT_2)
    MINXVALATTR = $(MINXVALATTR)+@double(@Value(_count))*($(MAXXVALATTR)-$(MINXVALATTR))/@Value(AttributeCount)
    MINYVALATTR = $(MAXYVALATTR)-$(HEIGHT)*2-2*$(HEIGHT_2)
    Box -> AttributeRemover_2
    Text -> AttributeRemover

Bookmark: Remove Attributes
AttributeRemover_2
    REMOVE_ATTRS = _ATTRLIST,AttributeCount,_count,_attr_name,_attr_value,_list_index
    LIST_ATTRS = _list{}
    -> Outline (output)
AttributeRemover
    REMOVE_ATTRS = _ATTRLIST,AttributeCount,_count,_attr_name,_attr_value,_list_index
    LIST_ATTRS = _list{}
    -> Text (output)
