FME workspace overzicht_voor_rapport.fmw

Parameters:
- DestDataset_JPEG = $(FME_MF_DIR_USERTYPED)producten   # Destination JPEG Folder
- SourceDataset_WMS = http://gng-ap713.nieuwegein.nl/mapproxy/service?REQUEST=GetCapabilities   # Source WMS (Web Map Service) URL
- WMS_IN_SEARCH_ENVELOPE_MINX_WMS = 133008.47500000001   # Minimum X
- WMS_IN_SEARCH_ENVELOPE_MINY_WMS = 450164.74900000001   # Minimum Y
- WMS_IN_SEARCH_ENVELOPE_MAXX_WMS = 134120.748931751   # Maximum X
- WMS_IN_SEARCH_ENVELOPE_MAXY_WMS = 451365.96299999999   # Maximum Y
- SourceDataset_ESRISHAPE = $(FME_MF_DIR)producten\vbo_points.shp   # Source Esri Shapefile(s)

Readers:
- WMS_1: WMS from $(SourceDataset_WMS) in EPSG:28992
- ESRISHAPE_1: ESRISHAPE from $(SourceDataset_ESRISHAPE) in EPSG:28992

Writers:
- JPEG_1: JPEG to $(DestDataset_JPEG) in EPSG:28992

basistopo (reader WMS_1)
    attributes: wms_service_name memo, wms_service_title memo, wms_service_abstract memo, wms_layer_name memo, wms_layer_title memo, wms_layer_abstract memo, wms_selected_layers set(basistopo)
    -> RasterExtractor
RasterExtractor
    RASTER_BLOB_ATTR = _rasterBlob
    RASTER_FORMAT = PNG (Portable Network Graphics)
    RASTER_FORMAT_ATTR = _rasterFormatName
    -> RasterBandAdder
RasterBandAdder
    INTERPRETATION = Alpha8
    CELL_VALUE = 255
    -> Sorter
vbo_points (reader ESRISHAPE_1)
    attributes: vbo_poi_ID short
    -> FeatureColorSetter
FeatureColorSetter
    MODE = Fixed
    COLOR = 1,0,0
    FILL_COLOR = 1,0,0
    COLORED -> ImageRasterizer
ImageRasterizer
    SPECIFY_GROUND_EXTENTS = Use input data ground extents
    ROWCOL_OR_CELLSIZE = CellSize
    ALPHA = 1
    ANTI_ALIASING = Yes
    BACKGROUND_ALPHA = 0
    Y_CELL_SIZE = 3.5
    BACKGROUND_COLOR = 0,0,0
    X_CELL_SIZE = 3.5
    FILL_WITH_NODATA = No
    INTERPRETATION_TYPE = RGBA32
    RASTER -> Sorter
Sorter
    SORT_PARM = fme_basename ALPHA DESCENDING
    SORTED -> RasterMosaicker
RasterMosaicker
    ACCUM_ATTRS_NAME = Get Attributes From One Representative Feature
    INTERPOLATION_TYPE_NAME = Nearest Neighbor
    NODATA_OVERWRITE = No
    COMPOSITE_USING_ALPHA_BAND_NAME = Yes
    MERGE_PALETTES_NAME = No
    SNAPPING_TYPE_NAME = Resample
    -> RasterSelector
RasterSelector
    SELECTION_MODE = Band and Palette List
    BAND_LIST = 3
    -> RasterBandRemover
RasterBandRemover
    -> rapport_foto (writer JPEG_1)
rapport_foto (writer JPEG_1)
    attributes: wms_service_name char(254), wms_service_title char(254), wms_service_abstract char(254), wms_layer_name char(254), wms_layer_title char(254), wms_layer_abstract char(254), wms_selected_layers char(15)
