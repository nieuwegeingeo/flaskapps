FME workspace adressen_binnen_wijk_export.fmw

Parameters:
- EMAIL = m.kselik@nieuwegein.nl   # Email
- WIJKEN_SELECT =   # Selecteer wijken
- COORDS = POLYGON((133871.80795898434 449883.83999999997,134698.36795898434 451160.64,135921.40795898435 450307.2,134731.96795898434 449487.36,133871.80795898434 449883.83999999997))   # Coordinaten
- TRANS_GARAGE =   # Transformator of garagebox
- POSTCODE =   # Postcode

Readers:
- ORACLE_SPATIAL_1: ORACLE_SPATIAL from vngp

Note: Als geen coordinaat, dan wijken.
Note: Selecteer wijk
Tester
    TEST_DESCRIPTION = ""
    TEST_MODE = Automatic
    BOOL_OP = AND
    TEST_CLAUSE = TEST @Value(WIJKNAAM) IN $(WIJKEN_SELECT)
    PASSED -> Tester_PASSED_-__SpatialFilter_Filter
Tester_PASSED_-__SpatialFilter_Filter: Junction
    -> SpatialFilter [Filter]

Bookmark: Oracle input
Creator_3
    GEOMTYPE = Geometry Object
    NUM = 1
    CREATED -> Tester_7
Note: Tester_7 [Tester] / Test Description: "" / TEST $(POSTCODE) ATTRIBUTE_HAS_VALUE "" / Condition: OR
Tester_7
    TEST_DESCRIPTION = ""
    TEST_MODE = Automatic
    BOOL_OP = OR
    TEST_CLAUSE = TEST $(POSTCODE) ATTRIBUTE_HAS_VALUE ""
    PASSED -> FeatureReader_4 [INITIATOR]
    PASSED -> Transformator_garage_creator [Creation_Input]
    FAILED -> Tester_2
FeatureReader
    ORACLE_SPATIAL_USE_UNIFIED_DATE_ATTRS = YES
    ORACLE_SPATIAL_PARSE_MAPINFO_SYMBOLOGY = NO
    ORACLE_SPATIAL_READ_3D_POLYGON_AS_FACE = NO
    ORACLE_SPATIAL_QUERY_FEATURE_TYPES_FOR_MERGE_FILTERS = Yes
    COMBINE_GEOM = Use Result
    ORACLE_SPATIAL_USER_NAME = NIEUWEGEIN
    ORACLE_SPATIAL_PERSISTENT_CONNECTION = YES
    ORACLE_SPATIAL_SHOW_SYSTEM_TABLES = NO
    INTERACT = <No Spatial Filter>
    ORACLE_SPATIAL_REMOVE_SCHEMA_QUALIFIER = NO
    FEATURETYPES = NIEUWEGEIN.GM_SP_WIJKEN
    ORACLE_SPATIAL_CLIP_TO_ENVELOPE = NO
    ORACLE_SPATIAL_HANDLE_MULTIPLE_SPATIAL_COLUMNS = NO
    ORACLE_SPATIAL_USE_SEARCH_ENVELOPE = NO
    ORACLE_SPATIAL_SERVER_TYPE = ORACLE8i
    ORACLE_SPATIAL_PASSWORD =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
    ATTRIBUTES = NIEUWEGEIN.GM_SP_WIJKEN,"WIJKKODE,WIJKNAAM,ADRESSEN,ID"
    ORACLE_SPATIAL_CHUNK_SIZE = 200
    FORMAT = ORACLE_SPATIAL
    OUTPUT_FEATURES_DISPLAY = Schema and Data Features
    ORACLE_SPATIAL_INTERRESULT = = 'TRUE'
    ATTR_ACCUM_MODE = Only Use Result
    ORACLE_SPATIAL_INTERACTION = ANYINTERACT
    DATASET = vngp
    NIEUWEGEIN.GM_SP_WIJKEN -> Tester
Tester_2_FAILED_-__FeatureReader_INITIATOR_Output_-__FeatureReader_5_INITIATOR: Junction
    -> FeatureReader_5 [INITIATOR]
Note: Transformator en garage features op basis van parameters
Transformator_garage_creator
    TRANS_GARAGE = $(TRANS_GARAGE)
    -> Tester_6
NIEUWEGEIN.GM_SP_WIJKEN (reader ORACLE_SPATIAL_1)
    attributes: WIJKKODE number(5,0), WIJKNAAM varchar2(50), ADRESSEN varchar2(50), ID number(5,0)
    -> NIEUWEGEIN.GM_SP_WIJKEN_-__GeometryFilter
    -> PointOnAreaOverlayer_2 [AREA]

Bookmark: Test op coordinaten
Note: Tester_2 [Tester] / Test Description: "" / TEST $(COORDS) ATTRIBUTE_HAS_VALUE "" / Condition: OR
Tester_2
    TEST_DESCRIPTION = ""
    TEST_MODE = Automatic
    BOOL_OP = OR
    TEST_CLAUSE = TEST $(COORDS) ATTRIBUTE_HAS_VALUE ""
    PASSED -> Tester_2_PASSED_-__GeometryReplacer_2
    FAILED -> Tester_2_FAILED_-__FeatureReader_INITIATOR
Tester_2_PASSED_-__GeometryReplacer_2: Junction
    -> GeometryReplacer_2
    -> Tester_2_FAILED_-__FeatureReader_INITIATOR_Output_-__FeatureReader_5_INITIATOR
Note: Toekennen wktstring parameter / $COORDS
GeometryReplacer_2
    KIND_LONG = OGC Well Known Text
    OGC_WKT_PRECISION_DISPLAY = 32-bit
    REMOVE_ATTRIBUTE = No
    SOURCE = $(COORDS)
    -> GeometryFilter_2
    <REJECTED> -> Terminator_2
GeometryFilter_2
    BREAK_AGG = No
    GEOM_PORT_NAMES = Area
    AREA -> GeometryValidator
GeometryValidator
    PRESETS = Custom
    REPAIR = Yes
    SELF_INTERSECTING = SELF_INTERSECTING
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    OGC_VALID_CHECK = OGC_VALID_CHECK
    CHECK_HOLE_TOUCHING_POLYGON = No
    ISSUE_ATTR_NAME = _issues
    PASSED -> Tester_PASSED_-__SpatialFilter_Filter
    FAILED -> Terminator_3
Terminator_3
    MESSAGE = Foutive geometrie
Terminator_2
    MESSAGE = Foutive geometrie
Tester_2_FAILED_-__FeatureReader_INITIATOR: Junction
    -> FeatureReader [INITIATOR]
    -> Tester_2_FAILED_-__FeatureReader_INITIATOR_Output_-__FeatureReader_5_INITIATOR

Bookmark: Test op wijken
FeatureReader_5
    ORACLE_SPATIAL_PARSE_MAPINFO_SYMBOLOGY = NO
    ORACLE_SPATIAL_USE_UNIFIED_DATE_ATTRS = YES
    ORACLE_SPATIAL_READ_3D_POLYGON_AS_FACE = NO
    ORACLE_SPATIAL_QUERY_FEATURE_TYPES_FOR_MERGE_FILTERS = Yes
    COMBINE_GEOM = Use Result
    ORACLE_SPATIAL_USER_NAME = NIEUWEGEIN
    ORACLE_SPATIAL_SHOW_SYSTEM_TABLES = NO
    ORACLE_SPATIAL_PERSISTENT_CONNECTION = YES
    INTERACT = <No Spatial Filter>
    ORACLE_SPATIAL_REMOVE_SCHEMA_QUALIFIER = NO
    FEATURETYPES = NIEUWEGEIN.GM_SP_BAG_ADRESSEN
    ORACLE_SPATIAL_CLIP_TO_ENVELOPE = NO
    ORACLE_SPATIAL_HANDLE_MULTIPLE_SPATIAL_COLUMNS = NO
    ORACLE_SPATIAL_USE_SEARCH_ENVELOPE = NO
    ORACLE_SPATIAL_SERVER_TYPE = ORACLE8i
    ORACLE_SPATIAL_PASSWORD =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
    ATTRIBUTES = NIEUWEGEIN.GM_SP_BAG_ADRESSEN,"ID,AUTH_AON,TYPE_AON,OBR_ID,OBR_NAAM,NAD_ID,NAD_HUISNUMMER,NAD_HUISLETTER,NAD_HUISNUMMERTOEVOEGING,NAD_POSTCODE,NAD_WIJKCODE,NAD_BUURTCODE,AUTH_STATUS_OBR,AUTH_STATUS_OA,AUTH_INGANGSDATUM,X_COORD_AO,Y_COORD_AO"
    FORMAT = ORACLE_SPATIAL
    OUTPUT_FEATURES_DISPLAY = Schema and Data Features
    ORACLE_SPATIAL_CHUNK_SIZE = 200
    ORACLE_SPATIAL_INTERRESULT = = 'TRUE'
    ATTR_ACCUM_MODE = Only Use Result
    ORACLE_SPATIAL_INTERACTION = ANYINTERACT
    DATASET = vngp
    NIEUWEGEIN.GM_SP_BAG_ADRESSEN -> Tester_8
Tester_8
    TEST_DESCRIPTION = ""
    TEST_MODE = Automatic
    BOOL_OP = OR
    TEST_CLAUSE = TEST @Value(NAD_HUISNUMMER) NOT_RANGE [7000,7999]
    PASSED -> GeometryFilter
GeometryFilter
    BREAK_AGG = No
    GEOM_PORT_NAMES = Point
    POINT -> PointOnAreaOverlayer [POINT]
NIEUWEGEIN.GM_SP_WIJKEN_-__GeometryFilter: Junction
    -> PointOnAreaOverlayer [AREA]
PointOnAreaOverlayer
    ATTR_ACCUM_MODE = Merge Incoming
    POLYS_FIRST = NO
    ATTR_CONFLICT_RES = Use Original
    POINT -> SpatialFilter [Candidate]

Bookmark: Test op postcode
Tester_6
    TEST_DESCRIPTION = ""
    TEST_MODE = Automatic
    BOOL_OP = OR
    TEST_CLAUSE = TEST $(POSTCODE) NOT_ATTRIBUTE_HAS_VALUE ""
    PASSED -> NIEUWEGEIN.GM_SP_WIJKEN_-__GeometryFilter
    FAILED -> Tester_5
Tester_5
    TEST_DESCRIPTION = ""
    TEST_MODE = Automatic
    BOOL_OP = OR
    TEST_CLAUSE = TEST @Value(NAD_POSTCODE) BEGINS_WITH $(POSTCODE)
    PASSED -> GeometryFilter_3
FeatureReader_4
    ORACLE_SPATIAL_PARSE_MAPINFO_SYMBOLOGY = NO
    ORACLE_SPATIAL_USE_UNIFIED_DATE_ATTRS = YES
    ORACLE_SPATIAL_READ_3D_POLYGON_AS_FACE = NO
    ORACLE_SPATIAL_QUERY_FEATURE_TYPES_FOR_MERGE_FILTERS = Yes
    COMBINE_GEOM = Use Result
    ORACLE_SPATIAL_USER_NAME = NIEUWEGEIN
    ORACLE_SPATIAL_SHOW_SYSTEM_TABLES = NO
    ORACLE_SPATIAL_PERSISTENT_CONNECTION = YES
    INTERACT = <No Spatial Filter>
    ORACLE_SPATIAL_REMOVE_SCHEMA_QUALIFIER = NO
    FEATURETYPES = NIEUWEGEIN.GM_SP_BAG_ADRESSEN
    WHERE = NAD_POSTCODE LIKE '%$(POSTCODE)%'
    ORACLE_SPATIAL_CLIP_TO_ENVELOPE = NO
    ORACLE_SPATIAL_HANDLE_MULTIPLE_SPATIAL_COLUMNS = NO
    ORACLE_SPATIAL_USE_SEARCH_ENVELOPE = NO
    ORACLE_SPATIAL_SERVER_TYPE = ORACLE8i
    ORACLE_SPATIAL_PASSWORD =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
    ATTRIBUTES = NIEUWEGEIN.GM_SP_BAG_ADRESSEN,"ID,AUTH_AON,TYPE_AON,OBR_ID,OBR_NAAM,NAD_ID,NAD_HUISNUMMER,NAD_HUISLETTER,NAD_HUISNUMMERTOEVOEGING,NAD_POSTCODE,NAD_WIJKCODE,NAD_BUURTCODE,AUTH_STATUS_OBR,AUTH_STATUS_OA,AUTH_INGANGSDATUM,X_COORD_AO,Y_COORD_AO"
    FORMAT = ORACLE_SPATIAL
    OUTPUT_FEATURES_DISPLAY = Schema and Data Features
    ORACLE_SPATIAL_CHUNK_SIZE = 200
    ORACLE_SPATIAL_INTERRESULT = = 'TRUE'
    ATTR_ACCUM_MODE = Only Use Result
    ORACLE_SPATIAL_INTERACTION = ANYINTERACT
    DATASET = vngp
    NIEUWEGEIN.GM_SP_BAG_ADRESSEN -> GeometryFilter_3
GeometryFilter_3
    BREAK_AGG = No
    GEOM_PORT_NAMES = Point
    POINT -> PointOnAreaOverlayer_2 [POINT]
PointOnAreaOverlayer_2
    ATTR_ACCUM_MODE = Merge Incoming
    POLYS_FIRST = NO
    ATTR_CONFLICT_RES = Use Original
    POINT -> DuplicateFilter

Bookmark: Mail adres tester
Note: Alleen @nieuwegein.nl adressen worden doorgelaten
Creator
    GEOMTYPE = Geometry Object
    NUM = 1
    CREATED -> Tester_3
Tester_3
    TEST_DESCRIPTION = ""
    TEST_MODE = Automatic
    BOOL_OP = OR
    TEST_CLAUSE = TEST $(EMAIL) LIKE %@nieuwegein.nl
    FAILED -> Terminator
Terminator
    MESSAGE = Translation Terminated

Bookmark: Selecteer op wijk of coordinaat
SpatialFilter
    BASE_TYPE = Multiple Filters
    PREDATTR = _predicate
    PASS_CRITERIA = Pass Against One Filter
    USE_BOUNDING_BOX = No
    ATTR_ACCUM_MODE = Merge Filter
    PREDICATES = INTERSECTS
    CURVE_BOUNDARY_RULE_PARAM = Default Rule
    ATTR_CONFLICT_RES = Use Candidate
    AGGREGATE_HANDLING = Yes
    PASSED -> DuplicateFilter
DuplicateFilter
    INPUT_ORDERED_CHOICE = No
    KEYATTR = NAD_ID
    UNIQUE -> AttributeManager
AttributeManager
    ATTR_TABLE:
      RENAME_SET_VALUE OBR_NAAM > STRAAT
      RENAME_SET_VALUE NAD_HUISNUMMER > HUISNUMMER
      RENAME_SET_VALUE NAD_HUISLETTER > HUISLETTER
      RENAME_SET_VALUE NAD_HUISNUMMERTOEVOEGING > HUISNUMMER TOEVOEGING
      RENAME_SET_VALUE NAD_POSTCODE > POSTCODE
      REMOVE NAD_WIJKCODE
      REMOVE NAD_BUURTCODE
      REMOVE AUTH_STATUS_OBR
      REMOVE AUTH_STATUS_OA
      REMOVE AUTH_INGANGSDATUM
      REMOVE X_COORD_AO
      REMOVE Y_COORD_AO
      REMOVE WIJKKODE
      REMOVE ADRESSEN
      REMOVE ID
      REMOVE AUTH_AON
      REMOVE TYPE_AON
      REMOVE _predicate
      REMOVE _creation_instance
      REMOVE OBR_ID
      REMOVE NAD_ID
    -> FeatureWriter [Output]

Bookmark: writer
FeatureWriter
    XLSXW_RASTER_FORMAT = PNG
    DATASET_ATTR = _dataset
    XLSXW_TEMPLATE_SHEET = Adressen
    XLSXW_DESTINATION_DATASETTYPE_VALIDATION = Yes
    XLSXW_WRITER_MODE = Insert
    DATASET = $(FME_MF_DIR_ENCODED)producten\adressen_download.xlsx
    XLSXW_TEMPLATEFILE = $(FME_MF_DIR)templates\adressen_template.xlsx
    XLSXW_TRUNCATE_TABLE = No
    FORMAT = XLSXW
    XLSXW_FIELD_NAMES_OUT = Yes
    TOTAL_FEATURES_WRITTEN_ATTR = _total_features_written
    XLSXW_OVERWRITE_FILE = No
    WRITER_DIRECTIVES = TRUNCATE_TABLE,No,RASTER_FORMAT,PNG,DESTINATION_DATASETTYPE_VALIDATION,Yes,TEMPLATE_SHEET,Adressen,DROP_TABLE,Yes,OVERWRITE_FILE,No,TEMPLATEFILE,$(FME_MF_DIR$encode)templates\adressen_template.xlsx,FIELD_NAMES_OUT,Yes,WRITER_MODE,Insert
    XLSXW_DROP_TABLE = Yes
    FEATURE_TYPE_LIST_ATTR = _feature_type
    SUMMARY -> Tester_4

Bookmark: Mailer
Tester_4
    TEST_DESCRIPTION = ""
    TEST_MODE = Automatic
    BOOL_OP = OR
    TEST_CLAUSE = TEST $(COORDS) ATTRIBUTE_HAS_VALUE ""
    PASSED -> StringConcatenator
    FAILED -> StringConcatenator_2
StringConcatenator
    ACTION = Create New Attribute
    VAL_ATTR = _result
    PARM_LINE:
      Hallo,

      Hierbij ontvangt u de adresgegevens binnen het geselecteerde gebied . Mocht u nog vragen hebben kunt u ons mailen op geo-informatie@nieuwegein.nl

      Met vriendelijke groet,

      Team Geo-Informatie
    -> PythonEmailer [TRIGGER]
StringConcatenator_2
    ACTION = Create New Attribute
    VAL_ATTR = _result
    PARM_LINE:
      Hallo,

      Hierbij ontvangt u de adresgegevens van de wijk(en) $(WIJKEN_SELECT). Mocht u nog vragen hebben kunt u ons mailen op geo-informatie@nieuwegein.nl

      Met vriendelijke groet,

      Team Geo-Informatie
    -> PythonEmailer [TRIGGER]
PythonEmailer
    cType = TLS
    email_message = @Value(_result)
    email_subject = Opgevraagde adresgegevens
    email_server = "smtp.nieuwegein.nl "
    email_from = geo-informatie@nieuwegein.nl
    email_message_type = plain
    email_to = $(EMAIL)
    attachments = @Value(_dataset)
    server_port = 25

FME custom transformer Transformator_garage_creator

Parameters:
- TRANS_GARAGE = transformator   # Transformator of garagebox

Creation_Input (input)
    -> Tester_5
    -> Tester_6
Tester_5
    TEST_DESCRIPTION = ""
    TEST_MODE = Automatic
    BOOL_OP = OR
    TEST_CLAUSE = TEST $(TRANS_GARAGE) CONTAINS transformator
    PASSED -> FeatureReader_2 [INITIATOR]
Note: Trans
FeatureReader_2
    ORACLE_SPATIAL_PARSE_MAPINFO_SYMBOLOGY = NO
    ORACLE_SPATIAL_USE_UNIFIED_DATE_ATTRS = YES
    ORACLE_SPATIAL_READ_3D_POLYGON_AS_FACE = NO
    ORACLE_SPATIAL_QUERY_FEATURE_TYPES_FOR_MERGE_FILTERS = Yes
    COMBINE_GEOM = Use Result
    ORACLE_SPATIAL_USER_NAME = NIEUWEGEIN
    ORACLE_SPATIAL_PERSISTENT_CONNECTION = YES
    ORACLE_SPATIAL_SHOW_SYSTEM_TABLES = NO
    INTERACT = <No Spatial Filter>
    ORACLE_SPATIAL_REMOVE_SCHEMA_QUALIFIER = NO
    FEATURETYPES = NIEUWEGEIN.GM_SP_BAG_ADRESSEN
    WHERE = NAD_HUISNUMMER BETWEEN 7000 AND 7999
    ORACLE_SPATIAL_CLIP_TO_ENVELOPE = NO
    ORACLE_SPATIAL_HANDLE_MULTIPLE_SPATIAL_COLUMNS = NO
    ORACLE_SPATIAL_USE_SEARCH_ENVELOPE = NO
    ORACLE_SPATIAL_SERVER_TYPE = ORACLE8i
    ORACLE_SPATIAL_PASSWORD =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
    ATTRIBUTES = NIEUWEGEIN.GM_SP_BAG_ADRESSEN,"ID,AUTH_AON,TYPE_AON,OBR_ID,OBR_NAAM,NAD_ID,NAD_HUISNUMMER,NAD_HUISLETTER,NAD_HUISNUMMERTOEVOEGING,NAD_POSTCODE,NAD_WIJKCODE,NAD_BUURTCODE,AUTH_STATUS_OBR,AUTH_STATUS_OA,AUTH_INGANGSDATUM,X_COORD_AO,Y_COORD_AO"
    ORACLE_SPATIAL_CHUNK_SIZE = 200
    FORMAT = ORACLE_SPATIAL
    OUTPUT_FEATURES_DISPLAY = Schema and Data Features
    ORACLE_SPATIAL_INTERRESULT = = 'TRUE'
    ATTR_ACCUM_MODE = Only Use Result
    ORACLE_SPATIAL_INTERACTION = ANYINTERACT
    DATASET = vngp
    NIEUWEGEIN.GM_SP_BAG_ADRESSEN -> Tester_3_PASSED_-__GeometryFilter
Tester_6
    TEST_DESCRIPTION = ""
    TEST_MODE = Automatic
    BOOL_OP = OR
    TEST_CLAUSE = TEST $(TRANS_GARAGE) CONTAINS garage
    PASSED -> FeatureReader_3 [INITIATOR]
Note: garage
FeatureReader_3
    ORACLE_SPATIAL_PARSE_MAPINFO_SYMBOLOGY = NO
    ORACLE_SPATIAL_USE_UNIFIED_DATE_ATTRS = YES
    ORACLE_SPATIAL_READ_3D_POLYGON_AS_FACE = NO
    ORACLE_SPATIAL_QUERY_FEATURE_TYPES_FOR_MERGE_FILTERS = Yes
    COMBINE_GEOM = Use Result
    ORACLE_SPATIAL_USER_NAME = NIEUWEGEIN
    ORACLE_SPATIAL_PERSISTENT_CONNECTION = YES
    ORACLE_SPATIAL_SHOW_SYSTEM_TABLES = NO
    INTERACT = <No Spatial Filter>
    ORACLE_SPATIAL_REMOVE_SCHEMA_QUALIFIER = NO
    FEATURETYPES = NIEUWEGEIN.GM_SP_BAG_ADRESSEN
    WHERE = NAD_HUISNUMMER BETWEEN 9000 AND 9999
    ORACLE_SPATIAL_CLIP_TO_ENVELOPE = NO
    ORACLE_SPATIAL_HANDLE_MULTIPLE_SPATIAL_COLUMNS = NO
    ORACLE_SPATIAL_USE_SEARCH_ENVELOPE = NO
    ORACLE_SPATIAL_SERVER_TYPE = ORACLE8i
    ORACLE_SPATIAL_PASSWORD =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
    ATTRIBUTES = NIEUWEGEIN.GM_SP_BAG_ADRESSEN,"ID,AUTH_AON,TYPE_AON,OBR_ID,OBR_NAAM,NAD_ID,NAD_HUISNUMMER,NAD_HUISLETTER,NAD_HUISNUMMERTOEVOEGING,NAD_POSTCODE,NAD_WIJKCODE,NAD_BUURTCODE,AUTH_STATUS_OBR,AUTH_STATUS_OA,AUTH_INGANGSDATUM,X_COORD_AO,Y_COORD_AO"
    ORACLE_SPATIAL_CHUNK_SIZE = 200
    FORMAT = ORACLE_SPATIAL
    OUTPUT_FEATURES_DISPLAY = Schema and Data Features
    ORACLE_SPATIAL_INTERRESULT = = 'TRUE'
    ATTR_ACCUM_MODE = Only Use Result
    ORACLE_SPATIAL_INTERACTION = ANYINTERACT
    DATASET = vngp
    NIEUWEGEIN.GM_SP_BAG_ADRESSEN -> Tester_3_PASSED_-__GeometryFilter
Tester_3_PASSED_-__GeometryFilter: Junction
    -> Output (output)
Output (output)

FME custom transformer PythonEmailer
This transformer sends emails that can contain attachments.
When a feature enters the PythonEmailer, it sends the file(s) set for its attachments parameter to the recipient(s). You can also include a custom message with the email.
This transformer uses code found at "http://dzone.com/snippets/send-email-attachments-python"
If you want this transformer to send the outputs of a writer in a workspace, encapsulate that workspace in a WorkspaceRunner transformer and make sure "Wait for Job To Complete" is set to "Yes", then connect the SUCCESS port of the WorkspaceRunner to PythonEmailer's Trigger port.
Attachments have to be entered as a list of comma separate values. For example: C:/file1.zip,C:/temp/file2.jpg
Recipients also have to be entered as a list of comma separated values.
If your email server does not need authentication, leave the Sender Username and Password parameters blank.
Attachments will have CID set to the base filename of the attached file, so you can embed them in an html message.
For example, if you attach c:\temp\file.jpg, you can embed it with
<img src="cid:file.jpg" />
in the HTML source for the message.
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_subject =   # Subject
- email_from =   # From
- attachments =   # Attachments
- email_to =   # Recipients
- email_server =   # Email Server
- server_port = 25   # Email Server Port
- cType = TLS   # Connection Type
- email_message =   # Email Message
- email_message_type = plain   # Email Message Type (Plain Text/HTML)
- username =   # Sender's Username
- password =   # Sender's Password

TRIGGER (input)
    -> ParameterFetcher
Note: Add parameters as attributes
ParameterFetcher
    ATTR_LIST = _email_subject {$(email_subject)} _email_from {$(email_from)} _Attachments {$(attachments)} _email_to {$(email_to)} _email_server {$(email_server)} _server_port {$(server_port)} _cType {$(cType)} _email_message {$(email_message)} _username {$(username)} _password {$(password)} _email_message_type {$(email_message_type)}
    -> PythonCaller
Note: Send mail.
PythonCaller
    PYTHONSYMBOL = email
    PYTHONSOURCE:
      # Original code found at "http://dzone.com/snippets/send-email-attachments-python" and modified by Arash Ouji.

      import smtplib, os, re
      from email.MIMEMultipart import MIMEMultipart
      from email.MIMEBase import MIMEBase
      from email.MIMEText import MIMEText
      from email.Utils import formatdate,COMMASPACE
      from email import Encoders

      # Main function
      def send_mail(send_from, send_to, subject, text, text_format, server, port, connection_type, username, password,attachments):

          # Create lists out of attachments and receipients strings
          filelist= re.split(",",attachments)
          tolist=re.split(",",send_to)

          # Create a container for the message and populate email headers
          msg = MIMEMultipart()
          msg['From'] = send_from
          msg['To'] = COMMASPACE.join(tolist)
          msg['Date'] = formatdate(localtime=True)
          msg['Subject'] = subject

          # Add email body text, forcing encoding to utf-8
          msg.attach( MIMEText(text,text_format,'utf-8') )

          # If there are any attachments, add them
          if (attachments!=''):
              for f in filelist:
                  part = MIMEBase('application', "octet-stream")
                  part.set_payload( open(f,"rb").read() )
                  Encoders.encode_base64(part)
                  part.add_header('Content-Disposition', 'attachment; filename="%s"' % os.path.basename(f))
                  part.add_header('Content-ID', '<%s>' % os.path.basename(f))
                  msg.attach(part)

          port = int (port)

          # Determine how we want to begin the connection
          if (connection_type=='TLS'):
              smtp=smtplib.SMTP(server,port)
          else:
              smtp = smtplib.SMTP_SSL(server,port)

          # If a username is provided, try to authenticate
          if (username!=''):
              smtp.login(username,password)

          # Send the email
          smtp.sendmail(send_from, tolist, msg.as_string())
          smtp.close()

      # Feature starting point
      def email(feature):

          # Retrieve all variables
          email_from=feature.getAttribute('_email_from')
          email_to=feature.getAttribute('_email_to')
          email_subject=feature.getAttribute('_email_subject')
          email_message=feature.getAttribute('_email_message')
          email_message_type=feature.getAttribute('_email_message_type')
          email_server=feature.getAttribute('_email_server')
          server_port=feature.getAttribute('_server_port')
          cType=feature.getAttribute('_cType')
          username=feature.getAttribute('_username')
          password=feature.getAttribute('_password')
          Attachments=feature.getAttribute('_Attachments')

          # Call the main function
          send_mail(email_from,email_to,email_subject,email_message,email_message_type,email_server,server_port,cType,username,password,Attachments)
