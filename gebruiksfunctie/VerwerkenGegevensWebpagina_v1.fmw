FME workspace VerwerkenGegevensWebpagina_v1.fmw

Parameters:
- COORDS = POLYGON((135213.12 450199.68,135045.12 449984.64,135327.36 449883.84,135508.8 450152.64,135213.12 450199.68))   # "134558.8545 450403.6628 134744.7243 450570.6146"%"134151.8183 447006.2135 137810.4403 449482.8191" Coordinate List
- VBO_GEB_FUNCTIE = woonfunctie   # gebruiksfunctie"%sportfunctie%winkelfunctie%woonfunctie Selecteer gebruiksfunctie
- OUTPUT_FORMAT = pdf   # Uitput formaat
- OUTPUT_DATA = "Adres en Oppervlakte en Gebruiksfunctie"
- SourceDataset_WMS = http://gng-ap713.nieuwegein.nl/mapproxy/service?   # Source WMS (Web Map Service) URL
- DestDataset_PDF2D = \\DL02EVA\GEO\GIS_onderzoek\2016\published_parameters\FME\Doel\pdf\rapport.pdf   # Destination Adobe Geospatial PDF File
- DestDataset_XLSXW = J:\GIS_onderzoek\2016\published_parameters\FME\Doel\Excel\rapport.xlsx   # Destination Microsoft Excel File

Readers:
- WMS_1: WMS from $(SourceDataset_WMS) in EPSG:28992

Writers:
- PDF2D_1: PDF2D to $(DestDataset_PDF2D) in EPSG:28992
- XLSXW_1: XLSXW to $(DestDataset_XLSXW)

Creator_2
    GEOMTYPE = Geometry Object
    GEOM = Null
    NUM = 1
    COORDSYS = EPSG:28992
    CREATED -> GeometryReplacer_2
Note: Toekennen wktstring parameter / $COORDS
GeometryReplacer_2
    KIND_LONG = OGC Well Known Text
    SOURCE = $(COORDS)
    OGC_WKT_PRECISION_DISPLAY = 32-bit
    REMOVE_ATTRIBUTE = No
    -> GeometryFilter
    -> GeometryReplacer_2_Output
AttributeCreator_ADRES
    ATTR_LIST = ADRES,"FME_CONDITIONAL:DEFAULT_VALUE'_FME_NO_OP_'BOOL_OP;AND;COMPOSITE_TEST;<Unused>;TEST HUISNUMMERTOEVOEGING ATTRIBUTE_VALUE_NULL _FME_BLANK_STRING_;TEST HUISLETTER ATTRIBUTE_VALUE_NULL _FME_BLANK_STRING_'@Value(OPENBARE_RUIMTE) @Value(HUISNUMMER) @Value(POSTCODE) @Value(WOONPLAATS)'BOOL_OP;OR;COMPOSITE_TEST;<Unused>;TEST HUISLETTER ATTRIBUTE_VALUE_NULL _FME_BLANK_STRING_'@Value(OPENBARE_RUIMTE) @Value(HUISNUMMER) @Value(HUISNUMMERTOEVOEGING) @Value(POSTCODE) @Value(WOONPLAATS)'BOOL_OP;OR;COMPOSITE_TEST;<Unused>;TEST HUISNUMMERTOEVOEGING ATTRIBUTE_VALUE_NULL _FME_BLANK_STRING_'@Value(OPENBARE_RUIMTE) @Value(HUISNUMMER) @Value(HUISLETTER) @Value(POSTCODE) @Value(WOONPLAATS)'FME_NUM_CONDITIONS4___"
    -> TestFilter_DATA_SELECTIE
    -> TestFilter_3
Note: opvangen selectie die geen waarde heeft / moet nog
TestFilter_DATA_SELECTIE
    TEST_LIST = BOOL_OP,OR,COMPOSITE_TEST,<Unused>,TEST_CLAUSE,"TEST @Value(_OUTPUT_DATA) = Adres",Adres,BOOL_OP,OR,COMPOSITE_TEST,<Unused>,TEST_CLAUSE,"TEST @Value(_OUTPUT_DATA) = "Adres en Gebruiksfunctie"",Adres en Gebruiksfunctie,BOOL_OP,OR,COMPOSITE_TEST,<Unused>,TEST_CLAUSE,"TEST @Value(_OUTPUT_DATA) = "Adres en Oppervlakte en Gebruiksfunctie"",Adres en Oppervlakte en Gebruiksfunctie,BOOL_OP,OR,COMPOSITE_TEST,<Unused>,TEST_CLAUSE,"TEST @Value(_OUTPUT_DATA) = "Adres en Oppervlakte"",Adres en Oppervlakte,BOOL_OP,OR,COMPOSITE_TEST,<Unused>,TEST_CLAUSE,"TEST @Value(_OUTPUT_DATA) = Gebruiksfunctie",Gebruiksfunctie,BOOL_OP,OR,COMPOSITE_TEST,<Unused>,TEST_CLAUSE,"TEST @Value(_OUTPUT_DATA) = Oppervlakte",Oppervlakte,BOOL_OP,OR,COMPOSITE_TEST,<Unused>,TEST_CLAUSE,"TEST @Value(_OUTPUT_DATA) = "Oppervlakte en Gebruikersfunctie"",Oppervlakte en Gebruikersfunctie
    DEFAULT_VALUE = <UNFILTERED>
    Adres -> AttributeKeeper
    Adres en Gebruiksfunctie -> AttributeKeeper_2
    Adres en Oppervlakte en Gebruiksfunctie -> AttributeKeeper_3
    Adres en Oppervlakte -> AttributeKeeper_4
    Gebruiksfunctie -> AttributeKeeper_5
    Oppervlakte -> AttributeKeeper_6
    Oppervlakte en Gebruikersfunctie -> AttributeKeeper_7
    <UNFILTERED> -> TestFilter_DATA_SELECTIE__Unfiltered_
AttributeKeeper
    KEEP_ATTRS = ADRES
    -> TestFilter_DATA_SELECTIE_Adres
TestFilter_DATA_SELECTIE_Adres: Inspector
AttributeKeeper_2
    KEEP_ATTRS = ADRES,GEBRUIK
    -> TestFilter_DATA_SELECTIE_Adres_en_Gebruiksfunctie
TestFilter_DATA_SELECTIE_Adres_en_Gebruiksfunctie: Inspector
AttributeKeeper_3
    KEEP_ATTRS = ADRES,GEBRUIK,OPPERVLAKTE
    -> TestFilter_DATA_SELECTIE_Adres_en_Oppervlakte_en_Gebruiksfunctie
TestFilter_DATA_SELECTIE_Adres_en_Oppervlakte_en_Gebruiksfunctie: Inspector
AttributeKeeper_4
    KEEP_ATTRS = ADRES,OPPERVLAKTE
    -> TestFilter_DATA_SELECTIE_Adres_en_Oppervlakte
TestFilter_DATA_SELECTIE_Adres_en_Oppervlakte: Inspector
AttributeKeeper_5
    KEEP_ATTRS = GEBRUIK
    -> TestFilter_DATA_SELECTIE_Gebruiksfunctie
TestFilter_DATA_SELECTIE_Gebruiksfunctie: Inspector
AttributeKeeper_6
    KEEP_ATTRS = OPPERVLAKTE
    -> TestFilter_DATA_SELECTIE_Oppervlakte
TestFilter_DATA_SELECTIE_Oppervlakte: Inspector
AttributeKeeper_7
    KEEP_ATTRS = OPPERVLAKTE,GEBRUIK
    -> TestFilter_DATA_SELECTIE_Oppervlakte_en_Gebruikersfunctie
TestFilter_DATA_SELECTIE_Oppervlakte_en_Gebruikersfunctie: Inspector [off]
TestFilter_DATA_SELECTIE__Unfiltered_: Inspector [off]
Note: _output_format
TestFilter_3
    TEST_LIST = BOOL_OP,OR,COMPOSITE_TEST,<Unused>,TEST_CLAUSE,"TEST @Value(_OUTPUT_FORMAT) = pdf",pdf,BOOL_OP,OR,COMPOSITE_TEST,<Unused>,TEST_CLAUSE,"TEST @Value(_OUTPUT_FORMAT) = xls",xls
    DEFAULT_VALUE = <UNFILTERED>
    pdf -> FEATURECOLORSETTER
    xls -> ADRESSEN (writer XLSXW_1)
FEATURECOLORSETTER: FeatureColorSetter
    MODE = Fixed
    COLOR = 1,0,0
    FILL_COLOR = 1,0,0
    COLORED -> ImageRasterizer
    COLORED -> FeatureColorSetter_Colored
    COLORED -> PDFPageFormatter [Colored]
FeatureColorSetter_Colored: Inspector [off]
ImageRasterizer
    FILL_WITH_NODATA = No
    X_CELL_SIZE = 1
    BACKGROUND_ALPHA = 0.0
    Y_CELL_SIZE = 1
    ANTI_ALIASING = No
    ALPHA = 1.0
    SPECIFY_GROUND_EXTENTS = Use input data ground extents
    TOLERANCE = 0.5
    BACKGROUND_COLOR = 1,1,1
    ROWCOL_OR_CELLSIZE = CellSize
    INTERPRETATION_TYPE = RGBA32
    RASTER -> ImageRasterizer_Raster
ImageRasterizer_Raster: Inspector [off]
ADRESSEN (writer XLSXW_1)
    attributes: ADRES auto(20)
Note: _output_format
TestFilter_2
    TEST_LIST = BOOL_OP,OR,COMPOSITE_TEST,<Unused>,TEST_CLAUSE,"TEST @Value(_OUTPUT_FORMAT) = pdf",pdf,BOOL_OP,OR,COMPOSITE_TEST,<Unused>,TEST_CLAUSE,"TEST @Value(_OUTPUT_FORMAT) = xls",xls
    DEFAULT_VALUE = <UNFILTERED>
    pdf -> BoundingBoxReplacer
    pdf -> PDFPageFormatter [geselecteerd gebied]
GeometryReplacer_2_Output: Inspector [off]
Note: Opmaak Pdf
basisluchtfoto (reader WMS_1)
    attributes: wms_service_name memo, wms_service_title memo, wms_service_abstract memo, wms_layer_name memo, wms_layer_title memo, wms_layer_abstract memo, wms_selected_layers set(basisluchtfoto)
    -> PDFPageFormatter [clipped_luchtfoto]
PDFPageFormatter
    PAGE_UNITS = Centimeters
    PAGE_ORIENTATION = Portrait
    PAGE_NUMBER = 1
    PAGE_OBJECTS = "clipped_luchtfoto FIXED_ASPECT;Yes;HEIGHT;215.36;MINX;155.37;MINY;504.335;WIDTH;286.13;SIZE_PARAMS;;SCALING_PARAMS;;CLIPPING_ENABLED;No","geselecteerd gebied FIXED_ASPECT;Yes;HEIGHT;220.62;MINX;149.375;MINY;501.259;WIDTH;292.12;SIZE_PARAMS;;SCALING_PARAMS;;CLIPPING_ENABLED;No","Colored FIXED_ASPECT;Yes;HEIGHT;210.77;MINX;149.42;MINY;505.285;WIDTH;287.63;SIZE_PARAMS;;SCALING_PARAMS;;CLIPPING_ENABLED;No"
    PAGE_WIDTH_PTS = 612
    PAGE_HEIGHT_PTS = 792
    PAGE_HEIGHT_USER = 27.94
    PAGE_WIDTH_USER = 21.59
    PAGE_SIZE = Letter
    -> rapport (writer PDF2D_1)
    -> PDFPageFormatter_Output
PDFPageFormatter_Output: Inspector [off]
rapport (writer PDF2D_1)
    attributes: wms_service_name string, wms_service_title string, wms_service_abstract string, wms_layer_name string, wms_layer_title string, wms_layer_abstract string, wms_selected_layers string

Bookmark: Validatie geometrie type en ggeldigheid
GeometryFilter
    GEOM_PORT_NAMES = Area
    BREAK_AGG = No
    AREA -> GeometryValidator [off]
    AREA -> ParameterFetcher
    <UNFILTERED> -> Logger_GeometryFilter_unfiltered
GeometryValidator
    REPAIR = Yes
    SELF_INTERSECTING = SELF_INTERSECTING
    CHECK_HOLE_TOUCHING_POLYGON = No
    PRESETS = Custom
    OGC_VALID_CHECK = OGC_VALID_CHECK
    ISSUE_ATTR_NAME = _issues
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PASSED -> ParameterFetcher
    FAILED -> Logger_GeometryValidator
    REPAIRED -> ParameterFetcher
Note: Na doen XML content
ParameterFetcher
    ATTR_LIST = _VBO_GEB_FUNCTIE {$(VBO_GEB_FUNCTIE)} _OUTPUT_DATA {$(OUTPUT_DATA)} _OUTPUT_FORMAT {$(OUTPUT_FORMAT)}
    -> AttributeSplitter
    -> TestFilter_2

Bookmark: Behoordelen parameter value
AttributeSplitter
    DROP_EMPTY_PARTS = No
    DELIMITER = " "
    ATTR_NAME = _VBO_GEB_FUNCTIE
    TRIM_OPTION = Both
    LIST_NAME = _list_VBO_GEB_FUNCTIE
    -> ListElementCounter
ListElementCounter
    CNT_ATTR = _element_count
    LIST_NAME = _list_VBO_GEB_FUNCTIE{}
    -> TestFilter
TestFilter
    TEST_LIST = BOOL_OP,OR,COMPOSITE_TEST,<Unused>,TEST_CLAUSE,"TEST @Value(_element_count) = 1",1,BOOL_OP,OR,COMPOSITE_TEST,<Unused>,TEST_CLAUSE,"TEST @Value(_element_count) > 1",N
    DEFAULT_VALUE = 0
    1 -> FeatureReader_GM_SP_BAG_VERBLIJFSOBJECTEN [INITIATOR]
    N -> GeometryExtractor_2
    0 -> TestFilter_0

Bookmark: Data ophalen
FeatureReader_GM_SP_BAG_VERBLIJFSOBJECTEN
    ORACLE_SPATIAL_PARSE_MAPINFO_SYMBOLOGY = NO
    ORACLE_SPATIAL_SERVER_TYPE = ORACLE8i
    ORACLE_SPATIAL_SHOW_SYSTEM_TABLES = NO
    ORACLE_SPATIAL_HANDLE_MULTIPLE_SPATIAL_COLUMNS = NO
    ATTR_CONFLICT_RES = Use Result
    ORACLE_SPATIAL_NAMED_CONNECTION = nieuwegeinvicrea@vngp
    ORACLE_SPATIAL_CHUNK_SIZE = 200
    FEATURETYPES_RADIO = FEATURETYPES
    ATTR_ACCUM_MODE = Merge Initiator and Result
    ORACLE_SPATIAL_PERSISTENT_CONNECTION = YES
    FORMAT = ORACLE_SPATIAL
    DATASET = nieuwegeinvicrea@vngp
    ORACLE_SPATIAL_REMOVE_SCHEMA_QUALIFIER = YES
    ORACLE_SPATIAL_USE_SEARCH_ENVELOPE = NO
    ORACLE_SPATIAL_CLIP_TO_ENVELOPE = NO
    ORACLE_SPATIAL_READ_3D_POLYGON_AS_FACE = NO
    WHERE = GEBRUIK LIKE ('%@Value(_VBO_GEB_FUNCTIE)%')
    COMBINE_GEOM = Use Result
    INTERACT = Intersects
    ATTRS_TO_EXPOSE = IDENTIFICATIECODE INGANGSDATUM OPENBARE_RUIMTE HUISNUMMER HUISLETTER HUISNUMMERTOEVOEGING POSTCODE WOONPLAATS STATUS STATUS_AUTHENTICITEIT DOCUMENT DOCUMENTDATUM INDICATIEGECONSTATEERD IN_ONDERZOEK_GEMEENTE OPPERVLAKTE GEBRUIK
    FEATURETYPES = GM_SP_BAG_VERBLIJFSOBJECTEN
    <OTHER> -> AttributeCreator_ADRES
FeatureReader_GM_SP_BAG_VERBLIJFSOBJECTEN_N
    ORACLE_SPATIAL_PARSE_MAPINFO_SYMBOLOGY = NO
    ORACLE_SPATIAL_SERVER_TYPE = ORACLE8i
    ORACLE_SPATIAL_SHOW_SYSTEM_TABLES = NO
    ORACLE_SPATIAL_HANDLE_MULTIPLE_SPATIAL_COLUMNS = NO
    ATTR_CONFLICT_RES = Use Result
    ORACLE_SPATIAL_NAMED_CONNECTION = nieuwegeinvicrea@vngp
    ORACLE_SPATIAL_CHUNK_SIZE = 200
    FEATURETYPES_RADIO = FEATURETYPES
    ATTR_ACCUM_MODE = Merge Initiator and Result
    ORACLE_SPATIAL_PERSISTENT_CONNECTION = YES
    FORMAT = ORACLE_SPATIAL
    DATASET = nieuwegeinvicrea@vngp
    ORACLE_SPATIAL_REMOVE_SCHEMA_QUALIFIER = YES
    ORACLE_SPATIAL_USE_SEARCH_ENVELOPE = NO
    ORACLE_SPATIAL_CLIP_TO_ENVELOPE = NO
    ORACLE_SPATIAL_READ_3D_POLYGON_AS_FACE = NO
    WHERE = @Value(_list_VBO_GEB_FUNCTIE2)
    COMBINE_GEOM = Use Result
    INTERACT = Intersects
    ATTRS_TO_EXPOSE = IDENTIFICATIECODE INGANGSDATUM OPENBARE_RUIMTE HUISNUMMER HUISLETTER HUISNUMMERTOEVOEGING POSTCODE WOONPLAATS STATUS STATUS_AUTHENTICITEIT DOCUMENT DOCUMENTDATUM INDICATIEGECONSTATEERD IN_ONDERZOEK_GEMEENTE OPPERVLAKTE GEBRUIK
    FEATURETYPES = GM_SP_BAG_VERBLIJFSOBJECTEN
    <OTHER> -> AttributeCreator_ADRES

Bookmark: Where clause LIKE - meerdere VBO gebruiksfuncies
GeometryExtractor_2
    ATTR = _geometry
    KIND_LONG = FME Binary
    OGC_WKT_PRECISION_DISPLAY = Shortened 64-bit
    -> GeometryRemover
GeometryRemover
    -> ListExploder
ListExploder
    ATTR_CONFLICT_RES = Use Original
    ATTR_ACCUM_MODE = Merge Incoming List
    LIST_ATTR = _list_VBO_GEB_FUNCTIE{}
    INDEX_ATTR = _element_index
    LIST_FOUND -> AttributeCreator
AttributeCreator
    ATTR_LIST = _list_VBO_GEB_FUNCTIE2,GEBRUIK LIKE '%@Value(_list_VBO_GEB_FUNCTIE)%'
    -> Aggregator
Aggregator
    ACCUM_ATTRS_NAME = Yes
    SEP = " OR \n "
    CONCAT_ATTRS = _list_VBO_GEB_FUNCTIE2
    ORDERED = No
    MODE = Attributes Only
    AGGREGATE -> GeometryReplacer
GeometryReplacer
    KIND_LONG = FME Binary
    SOURCE = @Value(_geometry)
    OGC_WKT_PRECISION_DISPLAY = 64-bit
    REMOVE_ATTRIBUTE = Yes
    -> FeatureReader_GM_SP_BAG_VERBLIJFSOBJECTEN_N [INITIATOR]

Bookmark: Ternimate
TestFilter_0: Logger
    MAXCOORDS = 20
    MESSAGE = Feature is:
    MAXFEATS = 20
    LOGGED -> Terminator
Terminator
    MESSAGE = Translation Terminated: geen waarde in de VBO functie gebruik parameter

Bookmark: test om wms te clippen met de bouds van de coords
BoundingBoxReplacer
    BOXTYPE = Bounding Box
    BOX -> BoundingBoxReplacer_Box
BoundingBoxReplacer_Box: Inspector [off]

Bookmark: Ternimate
Logger_GeometryValidator
    MAXCOORDS = 20
    MESSAGE = Feature is:
    MAXFEATS = 20
    LOGGED -> Terminator_GeometryFilter_2
Terminator_GeometryFilter_2 [off]
    MESSAGE:
      Translation Terminated: vlak geometrie niet valide
      @Value(_issues{0}.issue_found)

Bookmark: Ternimate
Logger_GeometryFilter_unfiltered
    MAXCOORDS = 20
    MESSAGE = Feature is:
    MAXFEATS = 20
    LOGGED -> Terminator_GeometryFilter
Terminator_GeometryFilter
    MESSAGE = Translation Terminated: geen vlak geometrie

FME custom transformer PythonEmailer
This transformer sends emails that can contain attachments.
When a feature enters the PythonEmailer, it sends the file(s) set for its attachments parameter to the recipient(s). You can also include a custom message with the email.
This transformer uses code found at "http://dzone.com/snippets/send-email-attachments-python"
If you want this transformer to send the outputs of a writer in a workspace, encapsulate that workspace in a WorkspaceRunner transformer and make sure "Wait for Job To Complete" is set to "Yes", then connect the SUCCESS port of the WorkspaceRunner to PythonEmailer's Trigger port.
Attachments have to be entered as a list of comma separate values. For example: C:/file1.zip,C:/temp/file2.jpg
Recipients also have to be entered as a list of comma separated values.
If your email server does not need authentication, leave the Sender Username and Password parameters blank.
Attachments will have CID set to the base filename of the attached file, so you can embed them in an html message.
For example, if you attach c:\temp\file.jpg, you can embed it with
<img src="cid:file.jpg" />
in the HTML source for the message.
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_subject =   # Subject
- email_from =   # From
- attachments =   # Attachments
- email_to =   # Recipients
- email_server =   # Email Server
- server_port = 25   # Email Server Port
- cType = TLS   # Connection Type
- email_message =   # Email Message
- email_message_type = plain   # Email Message Type (Plain Text/HTML)
- username =   # Sender's Username
- password =   # Sender's Password

TRIGGER (input)
    -> ParameterFetcher
Note: Add parameters as attributes
ParameterFetcher
    ATTR_LIST = _email_subject {$(email_subject)} _email_from {$(email_from)} _Attachments {$(attachments)} _email_to {$(email_to)} _email_server {$(email_server)} _server_port {$(server_port)} _cType {$(cType)} _email_message {$(email_message)} _username {$(username)} _password {$(password)} _email_message_type {$(email_message_type)}
    -> PythonCaller
Note: Send mail.
PythonCaller
    PYTHONSOURCE:
      # Original code found at "http://dzone.com/snippets/send-email-attachments-python" and modified by Arash Ouji.

      import smtplib, os, re
      from email.MIMEMultipart import MIMEMultipart
      from email.MIMEBase import MIMEBase
      from email.MIMEText import MIMEText
      from email.Utils import formatdate,COMMASPACE
      from email import Encoders

      # Main function
      def send_mail(send_from, send_to, subject, text, text_format, server, port, connection_type, username, password,attachments):

          # Create lists out of attachments and receipients strings
          filelist= re.split(",",attachments)
          tolist=re.split(",",send_to)

          # Create a container for the message and populate email headers
          msg = MIMEMultipart()
          msg['From'] = send_from
          msg['To'] = COMMASPACE.join(tolist)
          msg['Date'] = formatdate(localtime=True)
          msg['Subject'] = subject

          # Add email body text, forcing encoding to utf-8
          msg.attach( MIMEText(text,text_format,'utf-8') )

          # If there are any attachments, add them
          if (attachments!=''):
              for f in filelist:
                  part = MIMEBase('application', "octet-stream")
                  part.set_payload( open(f,"rb").read() )
                  Encoders.encode_base64(part)
                  part.add_header('Content-Disposition', 'attachment; filename="%s"' % os.path.basename(f))
                  part.add_header('Content-ID', '<%s>' % os.path.basename(f))
                  msg.attach(part)

          port = int (port)

          # Determine how we want to begin the connection
          if (connection_type=='TLS'):
              smtp=smtplib.SMTP(server,port)
          else:
              smtp = smtplib.SMTP_SSL(server,port)

          # If a username is provided, try to authenticate
          if (username!=''):
              smtp.login(username,password)

          # Send the email
          smtp.sendmail(send_from, tolist, msg.as_string())
          smtp.close()

      # Feature starting point
      def email(feature):

          # Retrieve all variables
          email_from=feature.getAttribute('_email_from')
          email_to=feature.getAttribute('_email_to')
          email_subject=feature.getAttribute('_email_subject')
          email_message=feature.getAttribute('_email_message')
          email_message_type=feature.getAttribute('_email_message_type')
          email_server=feature.getAttribute('_email_server')
          server_port=feature.getAttribute('_server_port')
          cType=feature.getAttribute('_cType')
          username=feature.getAttribute('_username')
          password=feature.getAttribute('_password')
          Attachments=feature.getAttribute('_Attachments')

          # Call the main function
          send_mail(email_from,email_to,email_subject,email_message,email_message_type,email_server,server_port,cType,username,password,Attachments)
    PYTHONSYMBOL = email
