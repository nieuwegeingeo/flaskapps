FME workspace OphalenGegevensWebpagina_v1.fmw

Parameters:
- COORDS = POLYGON((135213.12 450199.68,135045.12 449984.64,135327.36 449883.84,135508.8 450152.64,135213.12 450199.68))   # "134558.8545 450403.6628 134744.7243 450570.6146"%"134151.8183 447006.2135 137810.4403 449482.8191" Coordinate List
- VBO_GEB_FUNCTIE = woonfunctie   # gebruiksfunctie"%sportfunctie%winkelfunctie%woonfunctie Selecteer gebruiksfunctie
- OUTPUT_FORMAT = pdf   # Uitput formaat
- OUTPUT_DATA = "Adres en Oppervlakte en Gebruiksfunctie"
- EMAIL = T.Peet@Nieuwegein.nl   # email adres?

Creator
    GEOMTYPE = Geometry Object
    NUM = 1
    COORDSYS = EPSG:28992
    CREATED -> WorkspaceRunner
WorkspaceRunner
    BLOCKING = No
    WORKSPACE_FILE = $(FME_MF_DIR)VerwerkenGegevensWebpagina_v1.fmw
    WORKSPACE_PARAMETERS = COORDS,POLYGON((135213.12 450199.68,135045.12 449984.64,135327.36 449883.84,135508.8 450152.64,135213.12 450199.68)) ,VBO_GEB_FUNCTIE,woonfunctie,OUTPUT_FORMAT,xls,OUTPUT_DATA,"Adres en Oppervlakte en Gebruiksfunctie",SourceDataset_WMS,http://gng-ap713.nieuwegein.nl/mapproxy/service?,DestDataset_PDF2D,J:\GIS_onderzoek\2016\published_parameters\FME\Doel\pdf\rapport.pdf,DestDataset_XLSXW,rapport
    SUCCEEDED -> StringConcatenator
StringConcatenator
    ACTION = Create New Attribute
    PARM_LINE = $(COORDS) $(OUTPUT_DATA) $(OUTPUT_FORMAT) $(VBO_GEB_FUNCTIE) $(EMAIL)
    VAL_ATTR = _result
    -> TestFilter
TestFilter
    TEST_LIST = BOOL_OP,OR,COMPOSITE_TEST,<Unused>,TEST_CLAUSE,"TEST $(OUTPUT_FORMAT) = pdf",pdf,BOOL_OP,OR,COMPOSITE_TEST,<Unused>,TEST_CLAUSE,"TEST $(OUTPUT_FORMAT) = xls",xls
    DEFAULT_VALUE = <UNFILTERED>
    pdf -> AttributeCreator
    xls -> AttributeCreator_2
AttributeCreator
    ATTR_TABLE = SET_TO ATTACH_FILE = \\DL02EVA\GEO\GIS_onderzoek\2016\published_parameters\FME\Doel\pdf\rapport.pdf
    -> PythonEmailer [TRIGGER]
AttributeCreator_2
    ATTR_TABLE = SET_TO ATTACH_FILE = \\DL02EVA\GEO\GIS_onderzoek\2016\published_parameters\FME\Doel\Excel\rapport.xlsx
    -> PythonEmailer [TRIGGER]
PythonEmailer
    email_from = geo-informatie@nieuwegein.nl
    email_message = @Value(_result)
    email_subject = test
    server_port = 25
    email_message_type = plain
    email_to = $(EMAIL)
    email_server = "smtp.nieuwegein.nl "
    attachments = @Value(ATTACH_FILE)
    cType = TLS

FME custom transformer PythonEmailer
This transformer sends emails that can contain attachments.
When a feature enters the PythonEmailer, it sends the file(s) set for its attachments parameter to the recipient(s). You can also include a custom message with the email.
This transformer uses code found at "http://dzone.com/snippets/send-email-attachments-python"
If you want this transformer to send the outputs of a writer in a workspace, encapsulate that workspace in a WorkspaceRunner transformer and make sure "Wait for Job To Complete" is set to "Yes", then connect the SUCCESS port of the WorkspaceRunner to PythonEmailer's Trigger port.
Attachments have to be entered as a list of comma separate values. For example: C:/file1.zip,C:/temp/file2.jpg
Recipients also have to be entered as a list of comma separated values.
If your email server does not need authentication, leave the Sender Username and Password parameters blank.
Attachments will have CID set to the base filename of the attached file, so you can embed them in an html message.
For example, if you attach c:\temp\file.jpg, you can embed it with
<img src="cid:file.jpg" />
in the HTML source for the message.
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_subject =   # Subject
- email_from =   # From
- attachments =   # Attachments
- email_to =   # Recipients
- email_server =   # Email Server
- server_port = 25   # Email Server Port
- cType = TLS   # Connection Type
- email_message =   # Email Message
- email_message_type = plain   # Email Message Type (Plain Text/HTML)
- username =   # Sender's Username
- password =   # Sender's Password

TRIGGER (input)
    -> ParameterFetcher
Note: Add parameters as attributes
ParameterFetcher
    ATTR_LIST = _email_subject {$(email_subject)} _email_from {$(email_from)} _Attachments {$(attachments)} _email_to {$(email_to)} _email_server {$(email_server)} _server_port {$(server_port)} _cType {$(cType)} _email_message {$(email_message)} _username {$(username)} _password {$(password)} _email_message_type {$(email_message_type)}
    -> PythonCaller
Note: Send mail.
PythonCaller
    PYTHONSYMBOL = email
    PYTHONSOURCE:
      # Original code found at "http://dzone.com/snippets/send-email-attachments-python" and modified by Arash Ouji.

      import smtplib, os, re
      from email.MIMEMultipart import MIMEMultipart
      from email.MIMEBase import MIMEBase
      from email.MIMEText import MIMEText
      from email.Utils import formatdate,COMMASPACE
      from email import Encoders

      # Main function
      def send_mail(send_from, send_to, subject, text, text_format, server, port, connection_type, username, password,attachments):

          # Create lists out of attachments and receipients strings
          filelist= re.split(",",attachments)
          tolist=re.split(",",send_to)

          # Create a container for the message and populate email headers
          msg = MIMEMultipart()
          msg['From'] = send_from
          msg['To'] = COMMASPACE.join(tolist)
          msg['Date'] = formatdate(localtime=True)
          msg['Subject'] = subject

          # Add email body text, forcing encoding to utf-8
          msg.attach( MIMEText(text,text_format,'utf-8') )

          # If there are any attachments, add them
          if (attachments!=''):
              for f in filelist:
                  part = MIMEBase('application', "octet-stream")
                  part.set_payload( open(f,"rb").read() )
                  Encoders.encode_base64(part)
                  part.add_header('Content-Disposition', 'attachment; filename="%s"' % os.path.basename(f))
                  part.add_header('Content-ID', '<%s>' % os.path.basename(f))
                  msg.attach(part)

          port = int (port)

          # Determine how we want to begin the connection
          if (connection_type=='TLS'):
              smtp=smtplib.SMTP(server,port)
          else:
              smtp = smtplib.SMTP_SSL(server,port)

          # If a username is provided, try to authenticate
          if (username!=''):
              smtp.login(username,password)

          # Send the email
          smtp.sendmail(send_from, tolist, msg.as_string())
          smtp.close()

      # Feature starting point
      def email(feature):

          # Retrieve all variables
          email_from=feature.getAttribute('_email_from')
          email_to=feature.getAttribute('_email_to')
          email_subject=feature.getAttribute('_email_subject')
          email_message=feature.getAttribute('_email_message')
          email_message_type=feature.getAttribute('_email_message_type')
          email_server=feature.getAttribute('_email_server')
          server_port=feature.getAttribute('_server_port')
          cType=feature.getAttribute('_cType')
          username=feature.getAttribute('_username')
          password=feature.getAttribute('_password')
          Attachments=feature.getAttribute('_Attachments')

          # Call the main function
          send_mail(email_from,email_to,email_subject,email_message,email_message_type,email_server,server_port,cType,username,password,Attachments)
