FME workspace eigenaren_binnen_wijk_export.fmw

Parameters:
- EMAIL = m.kselik@Nieuwegein.nl   # Email
- LIST =   # " " list
- WIJKEN_SELECT = Batau Noord   # Selecteer wijken
- COORDS =   # Coordinaten
- SourceDataset_ORACLE_SPATIAL_1 = vngp   # Service Name or Easy Connect

Readers:
- ORACLE_SPATIAL_1: ORACLE_SPATIAL from $(SourceDataset_ORACLE_SPATIAL_1)

Note: Als geen coordinaat, dan wijken.
Note: Selecteer wijk
Tester
    TEST_MODE = Automatic
    BOOL_OP = OR
    TEST_CLAUSE = TEST @Value(WIJKNAAM) IN $(WIJKEN_SELECT)
    TEST_DESCRIPTION = ""
    PASSED -> SpatialFilter [Filter]
GeometryFilter
    BREAK_AGG = No
    GEOM_PORT_NAMES = Area
    AREA -> SpatialFilter [Candidate]
SpatialFilter
    CURVE_BOUNDARY_RULE_PARAM = Default Rule
    AGGREGATE_HANDLING = Yes
    BASE_TYPE = Multiple Filters
    PREDICATES = INTERSECTS
    PREDATTR = _predicate
    ATTR_CONFLICT_RES = Use Candidate
    ATTR_ACCUM_MODE = Merge Filter
    USE_BOUNDING_BOX = No
    PASS_CRITERIA = Pass Against One Filter
    PASSED -> AttributeManager
AttributeManager
    ATTR_TABLE:
      REMOVE WIJKKODE
      REMOVE ADRESSEN
      REMOVE ID
      REMOVE AUTH_AON
      REMOVE ID_BAG_PAND
      REMOVE ID_BAG_VBO
      REMOVE ID_GEBOUW
      REMOVE VERBLIJFSEENHEID_ID
      REMOVE VERBLIJFSEENHEIDVOLGNUMMER
      REMOVE VERBLIJFSEENHEIDNUMMER
      REMOVE GEBRUIK
      REMOVE STATUS_OMSCHRIJVING
      REMOVE VERDIEPING
      REMOVE WOONTYPE_OMSCHRIJVING
      REMOVE BESTEMMING
      REMOVE BOUWJAAR
      REMOVE STATUS_ID
      REMOVE VLOEROPPERVLAKTE
      REMOVE WONINGTYPE
      REMOVE WOONVERBLIJFSOORT
      REMOVE WOZOBJECTNUMMER
      REMOVE WOZBELOBJNR
      REMOVE OPPOBJECT
      REMOVE GEBRUIKCODE
      REMOVE OPPGEBOBJECT
      REMOVE WOONOPPERVLAKTE
      REMOVE FFWOZ
      REMOVE BIJZWRDCODE
      REMOVE CODEOBJECTSOORT
      REMOVE TYPE_AON
      REMOVE OPPERVLAKTE
      REMOVE BESTEMMING_OMSCHRIJVING
      REMOVE MONUMENT
      REMOVE DDTPEILDATUM
      REMOVE JJPEIL
      REMOVE JJBOUW
      REMOVE E_G
      REMOVE EIGENAAR_NAAM
      REMOVE E_SOFINR
      REMOVE E_SOFINR_EXTRA
      REMOVE E_PARTNER_NAAM
      REMOVE E_PARTNER_VOORV
      REMOVE E_STATUS
      REMOVE E_A_NR
      REMOVE E_DDOVERLIJDEN
      REMOVE GEBRUIKER_NAAM
      REMOVE G_SOFINR
      REMOVE G_NAAM
      REMOVE G_TITEL
      REMOVE G_VOORL
      REMOVE G_VOORV
      REMOVE G_PARTNER_NAAM
      REMOVE G_PARTNER_VOORV
      REMOVE G_SOFINR_EXTRA
      REMOVE G_KAD_SUBJECTNR
      REMOVE G_STATUS
      REMOVE G_A_NR
      REMOVE G_DDOVERLIJDEN
      REMOVE E_NATUURLIJK_P
      REMOVE G_NATUURLIJK_P
      REMOVE E_ADRES
      REMOVE G_ADRES
      REMOVE ADRES_WOZ
      REMOVE _predicate
      SET_TO EIGENAAR = FME_CONDITIONAL:DEFAULT_VALUE'_FME_NO_OP_'BOOL_OP;OR;COMPOSITE_TEST;<Unused>;TEST @Value(E_VOORL) = _FME_BLANK_STRING_'@Value(E_NAAM)'BOOL_OP;AND;COMPOSITE_TEST;<Unused>;TEST @Value(E_VOORL) ATTRIBUTE_HAS_VALUE _FME_BLANK_STRING_;TEST @Value(E_VOORV) = _FME_BLANK_STRING_'@Value(E_NAAM), @Value(E_VOORL)'BOOL_OP;AND;COMPOSITE_TEST;<Unused>;TEST @Value(E_VOORV) ATTRIBUTE_HAS_VALUE _FME_BLANK_STRING_'@Value(E_NAAM), @Value(E_VOORL) @Value(E_VOORV)'FME_NUM_CONDITIONS4___
    -> FeatureWriter [Output]
    -> SpatialFilter_Passed
SpatialFilter_Passed: Inspector [off]
Tester_4
    TEST_MODE = Automatic
    BOOL_OP = OR
    TEST_CLAUSE = TEST $(COORDS) ATTRIBUTE_HAS_VALUE ""
    TEST_DESCRIPTION = ""
    PASSED -> StringConcatenator
    FAILED -> StringConcatenator_2

Bookmark: Test op coordinaten
Creator_2
    NUM = 1
    GEOMTYPE = Geometry Object
    CREATED -> Tester_2
Tester_2
    TEST_MODE = Automatic
    BOOL_OP = OR
    TEST_CLAUSE = TEST $(COORDS) ATTRIBUTE_HAS_VALUE ""
    TEST_DESCRIPTION = ""
    PASSED -> GeometryReplacer_2
    FAILED -> FeatureReader [INITIATOR]
Note: Toekennen wktstring parameter / $COORDS
GeometryReplacer_2
    OGC_WKT_PRECISION_DISPLAY = 32-bit
    REMOVE_ATTRIBUTE = No
    KIND_LONG = OGC Well Known Text
    SOURCE = $(COORDS)
    -> GeometryFilter_2
    <REJECTED> -> Terminator_2
GeometryFilter_2
    BREAK_AGG = No
    GEOM_PORT_NAMES = Area
    AREA -> GeometryValidator
GeometryValidator
    PRESETS = Custom
    SELF_INTERSECTING = SELF_INTERSECTING
    OGC_VALID_CHECK = OGC_VALID_CHECK
    REPAIR = Yes
    CHECK_HOLE_TOUCHING_POLYGON = No
    ISSUE_ATTR_NAME = _issues
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PASSED -> SpatialFilter [Filter]
    FAILED -> Terminator_3
Terminator_3
    MESSAGE = Foutive geometrie
Terminator_2
    MESSAGE = Foutive geometrie

Bookmark: Oracle input
FeatureReader
    ATTRIBUTES = NIEUWEGEIN.GM_SP_WIJKEN,"WIJKKODE,WIJKNAAM,ADRESSEN,ID"
    ORACLE_SPATIAL_SERVER_TYPE = ORACLE8i
    ORACLE_SPATIAL_SHOW_SYSTEM_TABLES = NO
    ORACLE_SPATIAL_READ_3D_POLYGON_AS_FACE = NO
    DATASET = vngp
    INTERACT = <No Spatial Filter>
    OUTPUT_FEATURES_DISPLAY = Schema and Data Features
    ORACLE_SPATIAL_CHUNK_SIZE = 200
    ORACLE_SPATIAL_HANDLE_MULTIPLE_SPATIAL_COLUMNS = NO
    COMBINE_GEOM = Use Result
    ORACLE_SPATIAL_PARSE_MAPINFO_SYMBOLOGY = NO
    ORACLE_SPATIAL_INTERACTION = ANYINTERACT
    ORACLE_SPATIAL_INTERRESULT = = 'TRUE'
    FORMAT = ORACLE_SPATIAL
    ORACLE_SPATIAL_USE_UNIFIED_DATE_ATTRS = YES
    ORACLE_SPATIAL_CLIP_TO_ENVELOPE = NO
    FEATURETYPES = NIEUWEGEIN.GM_SP_WIJKEN
    ORACLE_SPATIAL_PERSISTENT_CONNECTION = YES
    ATTR_ACCUM_MODE = Only Use Result
    ORACLE_SPATIAL_PASSWORD =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
    ORACLE_SPATIAL_REMOVE_SCHEMA_QUALIFIER = NO
    ORACLE_SPATIAL_USE_SEARCH_ENVELOPE = NO
    ORACLE_SPATIAL_QUERY_FEATURE_TYPES_FOR_MERGE_FILTERS = Yes
    ORACLE_SPATIAL_USER_NAME = nieuwegein
    NIEUWEGEIN.GM_SP_WIJKEN -> Tester
NIEUWEGEIN.GM_SP_GEOOBJ_WOZOBJECTEIGENAAR (reader ORACLE_SPATIAL_1)
    attributes: AUTH_AON varchar2(16), ADRES varchar2(100), STRAAT varchar2(96), HUISNR number(38,0), HUISLT varchar2(4), TOEV varchar2(16), POSTCODE varchar2(6), WOONPL varchar2(160), WIJKNAAM varchar2(30), WIJKKODE number(2,0), ID_BAG_PAND varchar2(16), ID_BAG_VBO varchar2(16), ID_GEBOUW varchar2(16), VERBLIJFSEENHEID_ID number(38,0), VERBLIJFSEENHEIDVOLGNUMMER number(38,0), VERBLIJFSEENHEIDNUMMER varchar2(64), GEBRUIK nvarchar(50), STATUS_OMSCHRIJVING nvarchar(50), VERDIEPING varchar2(20), WOONTYPE_OMSCHRIJVING nvarchar(50), BESTEMMING varchar2(40), BOUWJAAR number(38,0), STATUS_ID number(38,0), VLOEROPPERVLAKTE number(38,0), WONINGTYPE number(38,0), WOONVERBLIJFSOORT number(38,0), WOZOBJECTNUMMER varchar2(160), WOZBELOBJNR number(38,0), OPPOBJECT number(38,0), GEBRUIKCODE number(38,0),
      OPPGEBOBJECT number(38,0), WOONOPPERVLAKTE number(38,0), FFWOZ number(38,0), BIJZWRDCODE number(38,0), CODEOBJECTSOORT varchar2(16), TYPE_AON nvarchar(20), OPPERVLAKTE number(10,0), BESTEMMING_OMSCHRIJVING nvarchar(200), MONUMENT varchar2(30), DDTPEILDATUM date, JJPEIL date, JJBOUW varchar2(36), E_G varchar2(100), EIGENAAR_NAAM varchar2(200), E_SOFINR number(38,0), E_NAAM varchar2(540), E_VOORL varchar2(40), E_VOORV varchar2(40), E_TITEL varchar2(8), E_SOFINR_EXTRA number(38,0), E_PARTNER_NAAM varchar2(200), E_PARTNER_VOORV varchar2(40), E_STATUS varchar2(4), E_A_NR number(38,0), E_DDOVERLIJDEN varchar2(32), GEBRUIKER_NAAM varchar2(200), G_SOFINR number(38,0), G_NAAM varchar2(540), G_TITEL varchar2(8), G_VOORL varchar2(40),
      G_VOORV varchar2(40), G_PARTNER_NAAM varchar2(200), G_PARTNER_VOORV varchar2(40), G_SOFINR_EXTRA number(38,0), G_KAD_SUBJECTNR number(38,0), G_STATUS varchar2(4), G_A_NR number(38,0), G_DDOVERLIJDEN varchar2(32), E_NATUURLIJK_P varchar2(10), G_NATUURLIJK_P varchar2(10), E_ADRES varchar2(100), G_ADRES varchar2(100), ADRES_WOZ varchar2(100)
    -> GeometryFilter

Bookmark: Mail adres tester
Note: Alleen @nieuwegein.nl adressen worden doorgelaten
Creator
    NUM = 1
    GEOMTYPE = Geometry Object
    CREATED -> Tester_3
Tester_3
    TEST_MODE = Automatic
    BOOL_OP = OR
    TEST_CLAUSE = TEST $(EMAIL) LIKE %@nieuwegein.nl
    TEST_DESCRIPTION = ""
    PASSED -> GeometryFilter
    FAILED -> Terminator
Terminator
    MESSAGE = Translation Terminated

Bookmark: writer
FeatureWriter
    FEATURE_TYPE_LIST_ATTR = _feature_type
    XLSXW_OVERWRITE_FILE = No
    XLSXW_TEMPLATE_SHEET = Eigenaren
    XLSXW_TRUNCATE_TABLE = No
    XLSXW_DROP_TABLE = Yes
    XLSXW_WRITER_MODE = Insert
    XLSXW_RASTER_FORMAT = PNG
    XLSXW_DESTINATION_DATASETTYPE_VALIDATION = Yes
    DATASET_ATTR = _dataset
    WRITER_DIRECTIVES = FIELD_NAMES_OUT,Yes,DROP_TABLE,Yes,OVERWRITE_FILE,No,TEMPLATEFILE,$(FME_MF_DIR$encode)templates\eigenaren_template.xlsx,TRUNCATE_TABLE,No,TEMPLATE_SHEET,Eigenaren,DESTINATION_DATASETTYPE_VALIDATION,Yes,WRITER_MODE,Insert,RASTER_FORMAT,PNG
    XLSXW_FIELD_NAMES_OUT = Yes
    DATASET = $(FME_MF_DIR_ENCODED)excel\WOZ_Eigenaren.xlsx
    TOTAL_FEATURES_WRITTEN_ATTR = _total_features_written
    FORMAT = XLSXW
    XLSXW_TEMPLATEFILE = $(FME_MF_DIR)templates\eigenaren_template.xlsx
    SUMMARY -> Tester_4

Bookmark: Mailer
StringConcatenator
    VAL_ATTR = _result
    PARM_LINE:
      Hallo,

      Hierbij ontvangt u de WOZ eigenaren binnen het geselecteerde gebied . Mocht u nog vragen hebben kunt u ons mailen op geo-informatie@nieuwegein.nl

      Met vriendelijke groet,

      Team Geo-Informatie
    ACTION = Create New Attribute
    -> PythonEmailer [TRIGGER]
StringConcatenator_2
    VAL_ATTR = _result
    PARM_LINE:
      Hallo,

      Hierbij ontvangt u de WOZ eigenaren van de wijk(en) $(WIJKEN_SELECT). Mocht u nog vragen hebben kunt u ons mailen op geo-informatie@nieuwegein.nl

      Met vriendelijke groet,

      Team Geo-Informatie
    ACTION = Create New Attribute
    -> PythonEmailer [TRIGGER]
PythonEmailer
    email_message_type = plain
    email_from = geo-informatie@nieuwegein.nl
    server_port = 25
    attachments = @Value(_dataset)
    email_server = "smtp.nieuwegein.nl "
    email_subject = "WOZ eigenaren "
    cType = TLS
    email_message = @Value(_result)
    email_to = $(EMAIL)

FME custom transformer PythonEmailer
This transformer sends emails that can contain attachments.
When a feature enters the PythonEmailer, it sends the file(s) set for its attachments parameter to the recipient(s). You can also include a custom message with the email.
This transformer uses code found at "http://dzone.com/snippets/send-email-attachments-python"
If you want this transformer to send the outputs of a writer in a workspace, encapsulate that workspace in a WorkspaceRunner transformer and make sure "Wait for Job To Complete" is set to "Yes", then connect the SUCCESS port of the WorkspaceRunner to PythonEmailer's Trigger port.
Attachments have to be entered as a list of comma separate values. For example: C:/file1.zip,C:/temp/file2.jpg
Recipients also have to be entered as a list of comma separated values.
If your email server does not need authentication, leave the Sender Username and Password parameters blank.
Attachments will have CID set to the base filename of the attached file, so you can embed them in an html message.
For example, if you attach c:\temp\file.jpg, you can embed it with
<img src="cid:file.jpg" />
in the HTML source for the message.
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_subject =   # Subject
- email_from =   # From
- attachments =   # Attachments
- email_to =   # Recipients
- email_server =   # Email Server
- server_port = 25   # Email Server Port
- cType = TLS   # Connection Type
- email_message =   # Email Message
- email_message_type = plain   # Email Message Type (Plain Text/HTML)
- username =   # Sender's Username
- password =   # Sender's Password

TRIGGER (input)
    -> ParameterFetcher
Note: Add parameters as attributes
ParameterFetcher
    ATTR_LIST = _email_subject {$(email_subject)} _email_from {$(email_from)} _Attachments {$(attachments)} _email_to {$(email_to)} _email_server {$(email_server)} _server_port {$(server_port)} _cType {$(cType)} _email_message {$(email_message)} _username {$(username)} _password {$(password)} _email_message_type {$(email_message_type)}
    -> PythonCaller
Note: Send mail.
PythonCaller
    PYTHONSYMBOL = email
    PYTHONSOURCE:
      # Original code found at "http://dzone.com/snippets/send-email-attachments-python" and modified by Arash Ouji.

      import smtplib, os, re
      from email.MIMEMultipart import MIMEMultipart
      from email.MIMEBase import MIMEBase
      from email.MIMEText import MIMEText
      from email.Utils import formatdate,COMMASPACE
      from email import Encoders

      # Main function
      def send_mail(send_from, send_to, subject, text, text_format, server, port, connection_type, username, password,attachments):

          # Create lists out of attachments and receipients strings
          filelist= re.split(",",attachments)
          tolist=re.split(",",send_to)

          # Create a container for the message and populate email headers
          msg = MIMEMultipart()
          msg['From'] = send_from
          msg['To'] = COMMASPACE.join(tolist)
          msg['Date'] = formatdate(localtime=True)
          msg['Subject'] = subject

          # Add email body text, forcing encoding to utf-8
          msg.attach( MIMEText(text,text_format,'utf-8') )

          # If there are any attachments, add them
          if (attachments!=''):
              for f in filelist:
                  part = MIMEBase('application', "octet-stream")
                  part.set_payload( open(f,"rb").read() )
                  Encoders.encode_base64(part)
                  part.add_header('Content-Disposition', 'attachment; filename="%s"' % os.path.basename(f))
                  part.add_header('Content-ID', '<%s>' % os.path.basename(f))
                  msg.attach(part)

          port = int (port)

          # Determine how we want to begin the connection
          if (connection_type=='TLS'):
              smtp=smtplib.SMTP(server,port)
          else:
              smtp = smtplib.SMTP_SSL(server,port)

          # If a username is provided, try to authenticate
          if (username!=''):
              smtp.login(username,password)

          # Send the email
          smtp.sendmail(send_from, tolist, msg.as_string())
          smtp.close()

      # Feature starting point
      def email(feature):

          # Retrieve all variables
          email_from=feature.getAttribute('_email_from')
          email_to=feature.getAttribute('_email_to')
          email_subject=feature.getAttribute('_email_subject')
          email_message=feature.getAttribute('_email_message')
          email_message_type=feature.getAttribute('_email_message_type')
          email_server=feature.getAttribute('_email_server')
          server_port=feature.getAttribute('_server_port')
          cType=feature.getAttribute('_cType')
          username=feature.getAttribute('_username')
          password=feature.getAttribute('_password')
          Attachments=feature.getAttribute('_Attachments')

          # Call the main function
          send_mail(email_from,email_to,email_subject,email_message,email_message_type,email_server,server_port,cType,username,password,Attachments)
