FME workspace OphalenGegevensWebpagina_v1.fmw

Parameters:
- COORDS = POLYGON((135213.12 450199.68,135045.12 449984.64,135327.36 449883.84,135508.8 450152.64,135213.12 450199.68))   # "134558.8545 450403.6628 134744.7243 450570.6146"%"134151.8183 447006.2135 137810.4403 449482.8191" Coordinate List
- VBO_GEB_FUNCTIE = woonfunctie   # gebruiksfunctie"%sportfunctie%winkelfunctie%woonfunctie Selecteer gebruiksfunctie
- OUTPUT_FORMAT = csv   # Uitput formaat
- OUTPUT_DATA = "Adres en Oppervlakte en Gebruiksfunctie"
- EMAIL = T.Peet@Nieuwegein.nl   # email adres?

Creator_2
    NUM = 1
    COORDSYS = EPSG:28992
    GEOM = Null
    GEOMTYPE = Geometry Object
    CREATED -> GeometryReplacer_2
Note: Toekennen wktstring parameter / $COORDS
GeometryReplacer_2
    SOURCE = $(COORDS)
    KIND_LONG = OGC Well Known Text
    OGC_WKT_PRECISION_DISPLAY = 32-bit
    REMOVE_ATTRIBUTE = No
    -> GeometryFilter
AttributeCreator_ADRES
    ATTR_LIST = ADRES,"FME_CONDITIONAL:DEFAULT_VALUE'_FME_NO_OP_'BOOL_OP;AND;COMPOSITE_TEST;<Unused>;TEST HUISNUMMERTOEVOEGING ATTRIBUTE_VALUE_NULL _FME_BLANK_STRING_;TEST HUISLETTER ATTRIBUTE_VALUE_NULL _FME_BLANK_STRING_'@Value(OPENBARE_RUIMTE) @Value(HUISNUMMER) @Value(POSTCODE) @Value(WOONPLAATS)'BOOL_OP;OR;COMPOSITE_TEST;<Unused>;TEST HUISLETTER ATTRIBUTE_VALUE_NULL _FME_BLANK_STRING_'@Value(OPENBARE_RUIMTE) @Value(HUISNUMMER) @Value(HUISNUMMERTOEVOEGING) @Value(POSTCODE) @Value(WOONPLAATS)'BOOL_OP;OR;COMPOSITE_TEST;<Unused>;TEST HUISNUMMERTOEVOEGING ATTRIBUTE_VALUE_NULL _FME_BLANK_STRING_'@Value(OPENBARE_RUIMTE) @Value(HUISNUMMER) @Value(HUISLETTER) @Value(POSTCODE) @Value(WOONPLAATS)'FME_NUM_CONDITIONS4___"
    -> TestFilter_DATA_SELECTIE
Note: opvangen selectie die geen waarde heeft / moet nog
TestFilter_DATA_SELECTIE
    TEST_LIST = BOOL_OP,OR,COMPOSITE_TEST,<Unused>,TEST_CLAUSE,"TEST @Value(_OUTPUT_DATA) = Adres",Adres,BOOL_OP,OR,COMPOSITE_TEST,<Unused>,TEST_CLAUSE,"TEST @Value(_OUTPUT_DATA) = "Adres en Gebruiksfunctie"",Adres en Gebruiksfunctie,BOOL_OP,OR,COMPOSITE_TEST,<Unused>,TEST_CLAUSE,"TEST @Value(_OUTPUT_DATA) = "Adres en Oppervlakte en Gebruiksfunctie"",Adres en Oppervlakte en Gebruiksfunctie,BOOL_OP,OR,COMPOSITE_TEST,<Unused>,TEST_CLAUSE,"TEST @Value(_OUTPUT_DATA) = "Adres en Oppervlakte"",Adres en Oppervlakte,BOOL_OP,OR,COMPOSITE_TEST,<Unused>,TEST_CLAUSE,"TEST @Value(_OUTPUT_DATA) = Gebruiksfunctie",Gebruiksfunctie,BOOL_OP,OR,COMPOSITE_TEST,<Unused>,TEST_CLAUSE,"TEST @Value(_OUTPUT_DATA) = Oppervlakte",Oppervlakte,BOOL_OP,OR,COMPOSITE_TEST,<Unused>,TEST_CLAUSE,"TEST @Value(_OUTPUT_DATA) = "Oppervlakte en Gebruikersfunctie"",Oppervlakte en Gebruikersfunctie
    DEFAULT_VALUE = <UNFILTERED>
    Adres -> AttributeKeeper
    Adres en Gebruiksfunctie -> AttributeKeeper_2
    Adres en Oppervlakte en Gebruiksfunctie -> AttributeKeeper_3
    Adres en Oppervlakte -> AttributeKeeper_4
    Gebruiksfunctie -> AttributeKeeper_5
    Oppervlakte -> AttributeKeeper_6
    Oppervlakte en Gebruikersfunctie -> AttributeKeeper_7
    <UNFILTERED> -> TestFilter_DATA_SELECTIE__Unfiltered_
AttributeKeeper
    KEEP_ATTRS = ADRES
    -> TestFilter_DATA_SELECTIE_Adres
TestFilter_DATA_SELECTIE_Adres: Inspector
AttributeKeeper_2
    KEEP_ATTRS = ADRES,GEBRUIK
    -> TestFilter_DATA_SELECTIE_Adres_en_Gebruiksfunctie
TestFilter_DATA_SELECTIE_Adres_en_Gebruiksfunctie: Inspector
AttributeKeeper_3
    KEEP_ATTRS = ADRES,GEBRUIK,OPPERVLAKTE
    -> TestFilter_DATA_SELECTIE_Adres_en_Oppervlakte_en_Gebruiksfunctie
TestFilter_DATA_SELECTIE_Adres_en_Oppervlakte_en_Gebruiksfunctie: Inspector
AttributeKeeper_4
    KEEP_ATTRS = ADRES,OPPERVLAKTE
    -> TestFilter_DATA_SELECTIE_Adres_en_Oppervlakte
TestFilter_DATA_SELECTIE_Adres_en_Oppervlakte: Inspector
AttributeKeeper_5
    KEEP_ATTRS = GEBRUIK
    -> TestFilter_DATA_SELECTIE_Gebruiksfunctie
TestFilter_DATA_SELECTIE_Gebruiksfunctie: Inspector
AttributeKeeper_6
    KEEP_ATTRS = OPPERVLAKTE
    -> TestFilter_DATA_SELECTIE_Oppervlakte
TestFilter_DATA_SELECTIE_Oppervlakte: Inspector
AttributeKeeper_7
    KEEP_ATTRS = OPPERVLAKTE,GEBRUIK
    -> TestFilter_DATA_SELECTIE_Oppervlakte_en_Gebruikersfunctie
TestFilter_DATA_SELECTIE_Oppervlakte_en_Gebruikersfunctie: Inspector
TestFilter_DATA_SELECTIE__Unfiltered_: Inspector
Note: Inhoud mail
StringConcatenator
    PARM_LINE = $(COORDS) $(OUTPUT_DATA) $(OUTPUT_FORMAT) $(VBO_GEB_FUNCTIE) $(EMAIL)
    ACTION = Create New Attribute
    VAL_ATTR = _result
    -> PythonEmailer [TRIGGER]
PythonEmailer
    cType = TLS
    server_port = 25
    email_to = $(EMAIL)
    email_message = @Value(_result)
    email_server = "smtp.nieuwegein.nl "
    email_from = geo-informatie@nieuwegein.nl
    email_subject = test
    email_message_type = plain

Bookmark: Validatie geometrie type en ggeldigheid
GeometryFilter
    GEOM_PORT_NAMES = Area
    BREAK_AGG = No
    AREA -> GeometryValidator [off]
    AREA -> ParameterFetcher
    <UNFILTERED> -> Logger_GeometryFilter_unfiltered
GeometryValidator
    CHECK_HOLE_TOUCHING_POLYGON = No
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    OGC_VALID_CHECK = OGC_VALID_CHECK
    PRESETS = Custom
    SELF_INTERSECTING = SELF_INTERSECTING
    REPAIR = Yes
    ISSUE_ATTR_NAME = _issues
    PASSED -> ParameterFetcher
    FAILED -> Logger_GeometryValidator
    REPAIRED -> ParameterFetcher
Note: Na doen XML content
ParameterFetcher
    ATTR_LIST = _VBO_GEB_FUNCTIE {$(VBO_GEB_FUNCTIE)} _OUTPUT_DATA {$(OUTPUT_DATA)} _OUTPUT_FORMAT {$(OUTPUT_FORMAT)}
    -> AttributeSplitter [off]
    -> StringConcatenator

Bookmark: Behoordelen parameter value
AttributeSplitter
    LIST_NAME = _list_VBO_GEB_FUNCTIE
    DROP_EMPTY_PARTS = No
    DELIMITER = " "
    TRIM_OPTION = Both
    ATTR_NAME = _VBO_GEB_FUNCTIE
    -> ListElementCounter
ListElementCounter
    CNT_ATTR = _element_count
    LIST_NAME = _list_VBO_GEB_FUNCTIE{}
    -> TestFilter
TestFilter
    TEST_LIST = BOOL_OP,OR,COMPOSITE_TEST,<Unused>,TEST_CLAUSE,"TEST @Value(_element_count) = 1",1,BOOL_OP,OR,COMPOSITE_TEST,<Unused>,TEST_CLAUSE,"TEST @Value(_element_count) > 1",N
    DEFAULT_VALUE = 0
    1 -> FeatureReader_GM_SP_BAG_VERBLIJFSOBJECTEN [INITIATOR]
    N -> GeometryExtractor_2
    0 -> TestFilter_0

Bookmark: Data ophalen
FeatureReader_GM_SP_BAG_VERBLIJFSOBJECTEN
    FORMAT = ORACLE_SPATIAL
    ORACLE_SPATIAL_USE_SEARCH_ENVELOPE = NO
    ORACLE_SPATIAL_PERSISTENT_CONNECTION = YES
    ORACLE_SPATIAL_SHOW_SYSTEM_TABLES = NO
    ORACLE_SPATIAL_CLIP_TO_ENVELOPE = NO
    ORACLE_SPATIAL_READ_3D_POLYGON_AS_FACE = NO
    ATTR_CONFLICT_RES = Use Result
    ATTR_ACCUM_MODE = Merge Initiator and Result
    INTERACT = Intersects
    ATTRS_TO_EXPOSE = IDENTIFICATIECODE INGANGSDATUM OPENBARE_RUIMTE HUISNUMMER HUISLETTER HUISNUMMERTOEVOEGING POSTCODE WOONPLAATS STATUS STATUS_AUTHENTICITEIT DOCUMENT DOCUMENTDATUM INDICATIEGECONSTATEERD IN_ONDERZOEK_GEMEENTE OPPERVLAKTE GEBRUIK
    ORACLE_SPATIAL_REMOVE_SCHEMA_QUALIFIER = YES
    ORACLE_SPATIAL_CHUNK_SIZE = 200
    COMBINE_GEOM = Use Result
    FEATURETYPES_RADIO = FEATURETYPES
    WHERE = GEBRUIK LIKE ('%@Value(_VBO_GEB_FUNCTIE)%')
    ORACLE_SPATIAL_NAMED_CONNECTION = nieuwegeinvicrea@vngp
    DATASET = nieuwegeinvicrea@vngp
    ORACLE_SPATIAL_HANDLE_MULTIPLE_SPATIAL_COLUMNS = NO
    ORACLE_SPATIAL_SERVER_TYPE = ORACLE8i
    FEATURETYPES = GM_SP_BAG_VERBLIJFSOBJECTEN
    ORACLE_SPATIAL_PARSE_MAPINFO_SYMBOLOGY = NO
    <OTHER> -> AttributeCreator_ADRES
FeatureReader_GM_SP_BAG_VERBLIJFSOBJECTEN_N
    FORMAT = ORACLE_SPATIAL
    ORACLE_SPATIAL_USE_SEARCH_ENVELOPE = NO
    ORACLE_SPATIAL_PERSISTENT_CONNECTION = YES
    ORACLE_SPATIAL_SHOW_SYSTEM_TABLES = NO
    ORACLE_SPATIAL_CLIP_TO_ENVELOPE = NO
    ORACLE_SPATIAL_READ_3D_POLYGON_AS_FACE = NO
    ATTR_CONFLICT_RES = Use Result
    ATTR_ACCUM_MODE = Merge Initiator and Result
    INTERACT = Intersects
    ATTRS_TO_EXPOSE = IDENTIFICATIECODE INGANGSDATUM OPENBARE_RUIMTE HUISNUMMER HUISLETTER HUISNUMMERTOEVOEGING POSTCODE WOONPLAATS STATUS STATUS_AUTHENTICITEIT DOCUMENT DOCUMENTDATUM INDICATIEGECONSTATEERD IN_ONDERZOEK_GEMEENTE OPPERVLAKTE GEBRUIK
    ORACLE_SPATIAL_REMOVE_SCHEMA_QUALIFIER = YES
    ORACLE_SPATIAL_CHUNK_SIZE = 200
    COMBINE_GEOM = Use Result
    FEATURETYPES_RADIO = FEATURETYPES
    WHERE = @Value(_list_VBO_GEB_FUNCTIE2)
    ORACLE_SPATIAL_NAMED_CONNECTION = nieuwegeinvicrea@vngp
    DATASET = nieuwegeinvicrea@vngp
    ORACLE_SPATIAL_HANDLE_MULTIPLE_SPATIAL_COLUMNS = NO
    ORACLE_SPATIAL_SERVER_TYPE = ORACLE8i
    FEATURETYPES = GM_SP_BAG_VERBLIJFSOBJECTEN
    ORACLE_SPATIAL_PARSE_MAPINFO_SYMBOLOGY = NO
    <OTHER> -> AttributeCreator_ADRES

Bookmark: Where clause LIKE - meerdere VBO gebruiksfuncies
GeometryExtractor_2
    ATTR = _geometry
    KIND_LONG = FME Binary
    OGC_WKT_PRECISION_DISPLAY = Shortened 64-bit
    -> GeometryRemover
GeometryRemover
    -> ListExploder
ListExploder
    ATTR_CONFLICT_RES = Use Original
    INDEX_ATTR = _element_index
    LIST_ATTR = _list_VBO_GEB_FUNCTIE{}
    ATTR_ACCUM_MODE = Merge Incoming List
    LIST_FOUND -> AttributeCreator
AttributeCreator
    ATTR_LIST = _list_VBO_GEB_FUNCTIE2,GEBRUIK LIKE '%@Value(_list_VBO_GEB_FUNCTIE)%'
    -> Aggregator
Aggregator
    MODE = Attributes Only
    ACCUM_ATTRS_NAME = Yes
    ORDERED = No
    SEP = " OR \n "
    CONCAT_ATTRS = _list_VBO_GEB_FUNCTIE2
    AGGREGATE -> GeometryReplacer
GeometryReplacer
    SOURCE = @Value(_geometry)
    KIND_LONG = FME Binary
    OGC_WKT_PRECISION_DISPLAY = 64-bit
    REMOVE_ATTRIBUTE = Yes
    -> FeatureReader_GM_SP_BAG_VERBLIJFSOBJECTEN_N [INITIATOR]

Bookmark: Ternimate
TestFilter_0: Logger
    MESSAGE = Feature is:
    MAXCOORDS = 20
    MAXFEATS = 20
    LOGGED -> Terminator
Terminator
    MESSAGE = Translation Terminated: geen waarde in de VBO functie gebruik parameter

Bookmark: Ternimate
Logger_GeometryValidator
    MESSAGE = Feature is:
    MAXCOORDS = 20
    MAXFEATS = 20
    LOGGED -> Terminator_GeometryFilter_2
Terminator_GeometryFilter_2 [off]
    MESSAGE:
      Translation Terminated: vlak geometrie niet valide
      @Value(_issues{0}.issue_found)

Bookmark: Ternimate
Logger_GeometryFilter_unfiltered
    MESSAGE = Feature is:
    MAXCOORDS = 20
    MAXFEATS = 20
    LOGGED -> Terminator_GeometryFilter
Terminator_GeometryFilter
    MESSAGE = Translation Terminated: geen vlak geometrie

FME custom transformer PythonEmailer
This transformer sends emails that can contain attachments.
When a feature enters the PythonEmailer, it sends the file(s) set for its attachments parameter to the recipient(s). You can also include a custom message with the email.
This transformer uses code found at "http://dzone.com/snippets/send-email-attachments-python"
If you want this transformer to send the outputs of a writer in a workspace, encapsulate that workspace in a WorkspaceRunner transformer and make sure "Wait for Job To Complete" is set to "Yes", then connect the SUCCESS port of the WorkspaceRunner to PythonEmailer's Trigger port.
Attachments have to be entered as a list of comma separate values. For example: C:/file1.zip,C:/temp/file2.jpg
Recipients also have to be entered as a list of comma separated values.
If your email server does not need authentication, leave the Sender Username and Password parameters blank.
Attachments will have CID set to the base filename of the attached file, so you can embed them in an html message.
For example, if you attach c:\temp\file.jpg, you can embed it with
<img src="cid:file.jpg" />
in the HTML source for the message.
Copyright (c) 2014 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- email_subject =   # Subject
- email_from =   # From
- attachments =   # Attachments
- email_to =   # Recipients
- email_server =   # Email Server
- server_port = 25   # Email Server Port
- cType = TLS   # Connection Type
- email_message =   # Email Message
- email_message_type = plain   # Email Message Type (Plain Text/HTML)
- username =   # Sender's Username
- password =   # Sender's Password

TRIGGER (input)
    -> ParameterFetcher
Note: Add parameters as attributes
ParameterFetcher
    ATTR_LIST = _email_subject {$(email_subject)} _email_from {$(email_from)} _Attachments {$(attachments)} _email_to {$(email_to)} _email_server {$(email_server)} _server_port {$(server_port)} _cType {$(cType)} _email_message {$(email_message)} _username {$(username)} _password {$(password)} _email_message_type {$(email_message_type)}
    -> PythonCaller
Note: Send mail.
PythonCaller
    PYTHONSOURCE:
      # Original code found at "http://dzone.com/snippets/send-email-attachments-python" and modified by Arash Ouji.

      import smtplib, os, re
      from email.MIMEMultipart import MIMEMultipart
      from email.MIMEBase import MIMEBase
      from email.MIMEText import MIMEText
      from email.Utils import formatdate,COMMASPACE
      from email import Encoders

      # Main function
      def send_mail(send_from, send_to, subject, text, text_format, server, port, connection_type, username, password,attachments):

          # Create lists out of attachments and receipients strings
          filelist= re.split(",",attachments)
          tolist=re.split(",",send_to)

          # Create a container for the message and populate email headers
          msg = MIMEMultipart()
          msg['From'] = send_from
          msg['To'] = COMMASPACE.join(tolist)
          msg['Date'] = formatdate(localtime=True)
          msg['Subject'] = subject

          # Add email body text, forcing encoding to utf-8
          msg.attach( MIMEText(text,text_format,'utf-8') )

          # If there are any attachments, add them
          if (attachments!=''):
              for f in filelist:
                  part = MIMEBase('application', "octet-stream")
                  part.set_payload( open(f,"rb").read() )
                  Encoders.encode_base64(part)
                  part.add_header('Content-Disposition', 'attachment; filename="%s"' % os.path.basename(f))
                  part.add_header('Content-ID', '<%s>' % os.path.basename(f))
                  msg.attach(part)

          port = int (port)

          # Determine how we want to begin the connection
          if (connection_type=='TLS'):
              smtp=smtplib.SMTP(server,port)
          else:
              smtp = smtplib.SMTP_SSL(server,port)

          # If a username is provided, try to authenticate
          if (username!=''):
              smtp.login(username,password)

          # Send the email
          smtp.sendmail(send_from, tolist, msg.as_string())
          smtp.close()

      # Feature starting point
      def email(feature):

          # Retrieve all variables
          email_from=feature.getAttribute('_email_from')
          email_to=feature.getAttribute('_email_to')
          email_subject=feature.getAttribute('_email_subject')
          email_message=feature.getAttribute('_email_message')
          email_message_type=feature.getAttribute('_email_message_type')
          email_server=feature.getAttribute('_email_server')
          server_port=feature.getAttribute('_server_port')
          cType=feature.getAttribute('_cType')
          username=feature.getAttribute('_username')
          password=feature.getAttribute('_password')
          Attachments=feature.getAttribute('_Attachments')

          # Call the main function
          send_mail(email_from,email_to,email_subject,email_message,email_message_type,email_server,server_port,cType,username,password,Attachments)
    PYTHONSYMBOL = email
